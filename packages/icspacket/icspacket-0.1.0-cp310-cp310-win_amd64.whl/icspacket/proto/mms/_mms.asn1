-- This ASN.1 file contains definitions for the following modules:
--  + MMS-Object-Module-1
--  + ISO-9506-MMS-1 and
--  + MMS-Environment-1

ISO-9506-MMS-1 { iso standard 9506 part(2) mms-abstract-syntax-version1(1) }
DEFINITIONS ::=
BEGIN

IMPORTS
AP-title,
AP-invocation-identifier,
AE-qualifier,
AE-invocation-identifier,
Authentication-value
FROM ACSE-1
{ joint-iso-itu-t association-control(2) modules(0) apdus(0) version1(1)};

-- EXPORTS AlternateAccess,
-- AttachToEventCondition,
-- AttachToSemaphore,
-- ConfirmedServiceRequest,
-- Data,
-- EE-State,
-- FileName,
-- Identifier,
-- Integer8,
-- Integer32,
-- MMSString,
-- MMS255String,
-- ObjectName,
-- TimeOfDay,
-- TypeSpecification,
-- Unsigned32,
-- Unsigned8,
-- VariableSpecification;

-- INLINED
-- IMPORTS ApplicationReference,
-- Authentication-value FROM
-- MMS-Environment-1 { iso standard 9506 part(2) mms-environment-version1 (4) }
-- ObtainFile-Request,
-- ObtainFile-Response,
-- ObtainFile-Error,
-- FileOpen-Request,
-- FileOpen-Response,
-- FileRead-Request,
-- FileRead-Response,
-- FileClose-Request,
-- FileClose-Response,
-- FileRename-Request,
-- FileRename-Response,
-- FileRename-Error,
-- FileDelete-Response,
-- FileDirectory-Request,
-- FileDirectory-Response,
-- DefineScatteredAccess-Request,
-- DefineScatteredAccess-Response,
-- ScatteredAccessDescription,
-- GetScatteredAccessAttributes-Request,
-- GetScatteredAccessAttributes-Response FROM
-- ISO-9506-MMS-1A { iso standard 9506 part(2) mms-annex-version1(3) }
-- AccessCondition,
-- AdditionalCBBOptions,
-- AdditionalSupportOptions,
-- Address,
-- AlarmAckRule,
-- Control-State,
-- DomainState,
-- EC-State,
-- EC-Class,
-- EE-Duration,
-- EE-Class,
-- EventTime,
-- Journal-Variable,
-- LogicalStatus,
-- Modifier,
-- normalPriority,
-- normalSeverity,
-- ParameterSupportOptions,
-- PhysicalStatus,
-- Priority,
-- ProgramInvocationState,
-- Running-Mode,
-- ServiceSupportOptions,
-- Severity,
-- Transitions,
-- TypeDescription,
-- ULState,
-- VMDState
-- FROM MMS-Object-Module-1
-- { iso standard 9506 part(1) mms-object-model-version1(2) };

EMBEDDED-PDV ::= [UNIVERSAL 11] SEQUENCE {
    identification       [0] CHOICE {
        syntaxes         [0] IMPLICIT SEQUENCE {
            abstract     OBJECT IDENTIFIER,
            transfer     OBJECT IDENTIFIER
        },
        syntax   [1] OBJECT IDENTIFIER,
        presentation-context-id  [2] INTEGER,
        context-negotiation      [3] IMPLICIT SEQUENCE {
            presentation-context-id      INTEGER,
            transfer-syntax      OBJECT IDENTIFIER
        },
        transfer-syntax  [4] OBJECT IDENTIFIER,
        fixed    [5] NULL
    },
    data-value   [1] OCTET STRING
}

TimeOfDay ::= OCTET STRING -- (SIZE(4 | 6))

-- This limit is not respected in implementations
maxIdentifier INTEGER ::= 32

Identifier ::= VisibleString -- (SIZE(1..maxIdentifier))

Integer8 ::= INTEGER (-128..127)

Integer16 ::= INTEGER (-32768..32767)

Integer32 ::= INTEGER (-2147483648..2147483647)

Unsigned8 ::= INTEGER (0..127)

Unsigned16 ::= INTEGER (0..32767)

Unsigned32 ::= INTEGER (0..2147483647)

ObjectName ::= CHOICE {
    vmd-specific	 [0] IMPLICIT Identifier,
    domain-specific	 [1] IMPLICIT SEQUENCE {
        domainID	 Identifier,
        itemID	 Identifier
    },
    aa-specific	 [2] IMPLICIT Identifier
}

ObjectClass ::= CHOICE {
    basicObjectClass	 [0] IMPLICIT INTEGER {
        namedVariable(0),
        scatteredAccess(1),
        namedVariableList(2),
        namedType(3),
        semaphore(4),
        eventCondition(5),
        eventAction(6),
        eventEnrollment(7),
        journal(8),
        domain(9),
        programInvocation(10),
        operatorStation(11),
        dataExchange(12),
        accessControlList(13)
    } (0..13),
    csObjectClass	 [1] IMPLICIT INTEGER {
        eventConditionList(0),
        unitControl(1)
    } (0..1)
}

MMSString ::= UTF8String

MMS255String ::= UTF8String (SIZE(1..255))

FileName ::= SEQUENCE OF GraphicString

MMSpdu ::= CHOICE {
    confirmed-RequestPDU	 [0] IMPLICIT Confirmed-RequestPDU,
    confirmed-ResponsePDU	 [1] IMPLICIT Confirmed-ResponsePDU,
    confirmed-ErrorPDU	 [2] IMPLICIT Confirmed-ErrorPDU,
    unconfirmed-PDU	 [3] IMPLICIT Unconfirmed-PDU,
    rejectPDU	 [4] IMPLICIT RejectPDU,
    cancel-RequestPDU	 [5] IMPLICIT Cancel-RequestPDU,
    cancel-ResponsePDU	 [6] IMPLICIT Cancel-ResponsePDU,
    cancel-ErrorPDU	 [7] IMPLICIT Cancel-ErrorPDU,
    initiate-RequestPDU	 [8] IMPLICIT Initiate-RequestPDU,
    initiate-ResponsePDU	 [9] IMPLICIT Initiate-ResponsePDU,
    initiate-ErrorPDU	 [10] IMPLICIT Initiate-ErrorPDU,
    conclude-RequestPDU	 [11] IMPLICIT Conclude-RequestPDU,
    conclude-ResponsePDU	 [12] IMPLICIT Conclude-ResponsePDU,
    conclude-ErrorPDU	 [13] IMPLICIT Conclude-ErrorPDU
}

Confirmed-RequestPDU ::= SEQUENCE {
    invokeID	 Unsigned32,
    listOfModifiers	 SEQUENCE OF Modifier OPTIONAL,
    service	 ConfirmedServiceRequest,
    service-ext	 [79] Request-Detail OPTIONAL
}

Confirmed-ErrorPDU ::= SEQUENCE {
    invokeID	 [0] IMPLICIT Unsigned32,
    modifierPosition	 [1] IMPLICIT Unsigned32 OPTIONAL,
    serviceError	 [2] IMPLICIT ServiceError
}

ConfirmedServiceRequest ::= CHOICE {
    status	 [0] IMPLICIT Status-Request,
    getNameList	 [1] IMPLICIT GetNameList-Request,
    identify	 [2] IMPLICIT Identify-Request,
    rename	 [3] IMPLICIT Rename-Request,
    read	 [4] IMPLICIT Read-Request,
    write	 [5] IMPLICIT Write-Request,
    getVariableAccessAttributes	 [6] GetVariableAccessAttributes-Request,
    defineNamedVariable	 [7] IMPLICIT DefineNamedVariable-Request,
    defineScatteredAccess	 [8] IMPLICIT DefineScatteredAccess-Request,
    getScatteredAccessAttributes	 [9] GetScatteredAccessAttributes-Request,
    deleteVariableAccess	 [10] IMPLICIT DeleteVariableAccess-Request,
    defineNamedVariableList	 [11] IMPLICIT DefineNamedVariableList-Request,
    getNamedVariableListAttributes	 [12] GetNamedVariableListAttributes-Request,
    deleteNamedVariableList	 [13] IMPLICIT DeleteNamedVariableList-Request,
    defineNamedType	 [14] IMPLICIT DefineNamedType-Request,
    getNamedTypeAttributes	 [15] GetNamedTypeAttributes-Request,
    deleteNamedType	 [16] IMPLICIT DeleteNamedType-Request,
    input	 [17] IMPLICIT Input-Request,
    output	 [18] IMPLICIT Output-Request,
    takeControl	 [19] IMPLICIT TakeControl-Request,
    relinquishControl	 [20] IMPLICIT RelinquishControl-Request,
    defineSemaphore	 [21] IMPLICIT DefineSemaphore-Request,
    deleteSemaphore	 [22] DeleteSemaphore-Request,
    reportSemaphoreStatus	 [23] ReportSemaphoreStatus-Request,
    reportPoolSemaphoreStatus	 [24] IMPLICIT ReportPoolSemaphoreStatus-Request,
    reportSemaphoreEntryStatus	 [25] IMPLICIT ReportSemaphoreEntryStatus-Request,
    initiateDownloadSequence	 [26] IMPLICIT InitiateDownloadSequence-Request,
    downloadSegment	 [27] IMPLICIT DownloadSegment-Request,
    terminateDownloadSequence	 [28] IMPLICIT TerminateDownloadSequence-Request,
    initiateUploadSequence	 [29] IMPLICIT InitiateUploadSequence-Request,
    uploadSegment	 [30] IMPLICIT UploadSegment-Request,
    terminateUploadSequence	 [31] IMPLICIT TerminateUploadSequence-Request,
    requestDomainDownload	 [32] IMPLICIT RequestDomainDownload-Request,
    requestDomainUpload	 [33] IMPLICIT RequestDomainUpload-Request,
    loadDomainContent	 [34] IMPLICIT LoadDomainContent-Request,
    storeDomainContent	 [35] IMPLICIT StoreDomainContent-Request,
    deleteDomain	 [36] IMPLICIT DeleteDomain-Request,
    getDomainAttributes	 [37] IMPLICIT GetDomainAttributes-Request,
    createProgramInvocation	 [38] IMPLICIT CreateProgramInvocation-Request,
    deleteProgramInvocation	 [39] IMPLICIT DeleteProgramInvocation-Request,
    start	 [40] IMPLICIT Start-Request,
    stop	 [41] IMPLICIT Stop-Request,
    resume	 [42] IMPLICIT Resume-Request,
    reset	 [43] IMPLICIT Reset-Request,
    kill	 [44] IMPLICIT Kill-Request,
    getProgramInvocationAttributes	 [45] IMPLICIT GetProgramInvocationAttributes-Request,
    obtainFile	 [46] IMPLICIT ObtainFile-Request,
    defineEventCondition	 [47] IMPLICIT DefineEventCondition-Request,
    deleteEventCondition	 [48] DeleteEventCondition-Request,
    getEventConditionAttributes	 [49] GetEventConditionAttributes-Request,
    reportEventConditionStatus	 [50] ReportEventConditionStatus-Request,
    alterEventConditionMonitoring	 [51] IMPLICIT AlterEventConditionMonitoring-Request,
    triggerEvent	 [52] IMPLICIT TriggerEvent-Request,
    defineEventAction	 [53] IMPLICIT DefineEventAction-Request,
    deleteEventAction	 [54] DeleteEventAction-Request,
    getEventActionAttributes	 [55] GetEventActionAttributes-Request,
    reportEventActionStatus	 [56] ReportEventActionStatus-Request,
    defineEventEnrollment	 [57] IMPLICIT DefineEventEnrollment-Request,
    deleteEventEnrollment	 [58] DeleteEventEnrollment-Request,
    alterEventEnrollment	 [59] IMPLICIT AlterEventEnrollment-Request,
    reportEventEnrollmentStatus	 [60] ReportEventEnrollmentStatus-Request,
    getEventEnrollmentAttributes	 [61] IMPLICIT GetEventEnrollmentAttributes-Request,
    acknowledgeEventNotification	 [62] IMPLICIT AcknowledgeEventNotification-Request,
    getAlarmSummary	 [63] IMPLICIT GetAlarmSummary-Request,
    getAlarmEnrollmentSummary	 [64] IMPLICIT GetAlarmEnrollmentSummary-Request,
    readJournal	 [65] IMPLICIT ReadJournal-Request,
    writeJournal	 [66] IMPLICIT WriteJournal-Request,
    initializeJournal	 [67] IMPLICIT InitializeJournal-Request,
    reportJournalStatus	 [68] ReportJournalStatus-Request,
    createJournal	 [69] IMPLICIT CreateJournal-Request,
    deleteJournal	 [70] IMPLICIT DeleteJournal-Request,
    getCapabilityList	 [71] IMPLICIT GetCapabilityList-Request,
    fileOpen	 [72] IMPLICIT FileOpen-Request,
    fileRead	 [73] IMPLICIT FileRead-Request,
    fileClose	 [74] IMPLICIT FileClose-Request,
    fileRename	 [75] IMPLICIT FileRename-Request,
    fileDelete	 [76] IMPLICIT FileDelete-Request,
    fileDirectory	 [77] IMPLICIT FileDirectory-Request,
    additionalService	 [78] AdditionalService-Request,
    getDataExchangeAttributes	 [80] GetDataExchangeAttributes-Request,
    exchangeData	 [81] IMPLICIT ExchangeData-Request,
    defineAccessControlList	 [82] IMPLICIT DefineAccessControlList-Request,
    getAccessControlListAttributes	 [83] GetAccessControlListAttributes-Request,
    reportAccessControlledObjects	 [84] IMPLICIT ReportAccessControlledObjects-Request,
    deleteAccessControlList	 [85] IMPLICIT DeleteAccessControlList-Request,
    changeAccessControl	 [86] IMPLICIT ChangeAccessControl-Request
}

AdditionalService-Request ::= CHOICE {
    vMDStop	 [0] IMPLICIT VMDStop-Request,
    vMDReset	 [1] IMPLICIT VMDReset-Request,
    select	 [2] IMPLICIT Select-Request,
    alterPI	 [3] IMPLICIT AlterProgramInvocationAttributes-Request,
    initiateUCLoad	 [4] IMPLICIT InitiateUnitControlLoad-Request,
    uCLoad	 [5] IMPLICIT UnitControlLoadSegment-Request,
    uCUpload	 [6] IMPLICIT UnitControlUpload-Request,
    startUC	 [7] IMPLICIT StartUnitControl-Request,
    stopUC	 [8] IMPLICIT StopUnitControl-Request,
    createUC	 [9] IMPLICIT CreateUnitControl-Request,
    addToUC	 [10] IMPLICIT AddToUnitControl-Request,
    removeFromUC	 [11] IMPLICIT RemoveFromUnitControl-Request,
    getUCAttributes	 [12] IMPLICIT GetUnitControlAttributes-Request,
    loadUCFromFile	 [13] IMPLICIT LoadUnitControlFromFile-Request,
    storeUCToFile	 [14] IMPLICIT StoreUnitControlToFile-Request,
    deleteUC	 [15] IMPLICIT DeleteUnitControl-Request,
    defineECL	 [16] DefineEventConditionList-Request,
    deleteECL	 [17] DeleteEventConditionList-Request,
    addECLReference	 [18] IMPLICIT AddEventConditionListReference-Request,
    removeECLReference	 [19] IMPLICIT RemoveEventConditionListReference-Request,
    getECLAttributes	 [20] GetEventConditionListAttributes-Request,
    reportECLStatus	 [21] IMPLICIT ReportEventConditionListStatus-Request,
    alterECLMonitoring	 [22] IMPLICIT AlterEventConditionListMonitoring-Request
}

Request-Detail ::= CHOICE {
    otherRequests	 NULL,
    createProgramInvocation	 [38] IMPLICIT CS-CreateProgramInvocation-Request,
    start	 [40] IMPLICIT CS-Start-Request,
    resume	 [42] IMPLICIT CS-Resume-Request,
    defineEventCondition	 [47] IMPLICIT CS-DefineEventCondition-Request,
    alterEventConditionMonitoring	 [51] IMPLICIT CS-AlterEventConditionMonitoring-Request,
    defineEventEnrollment	 [57] IMPLICIT CS-DefineEventEnrollment-Request,
    alterEventEnrollment	 [59] IMPLICIT CS-AlterEventEnrollment-Request
}

Unconfirmed-PDU ::= SEQUENCE {
    service	 UnconfirmedService,
    service-ext	 [79] Unconfirmed-Detail OPTIONAL
}

UnconfirmedService ::= CHOICE {
    informationReport	 [0] IMPLICIT InformationReport,
    unsolicitedStatus	 [1] IMPLICIT UnsolicitedStatus,
    eventNotification	 [2] IMPLICIT EventNotification
}

Unconfirmed-Detail ::= CHOICE {
    otherRequests	 NULL,
    eventNotification	 [2] IMPLICIT CS-EventNotification
}

Confirmed-ResponsePDU ::= SEQUENCE {
    invokeID	 Unsigned32,
    service	 ConfirmedServiceResponse,
    service-ext	 [79] Response-Detail OPTIONAL
}

ConfirmedServiceResponse ::= CHOICE {
    status	 [0] IMPLICIT Status-Response,
    getNameList	 [1] IMPLICIT GetNameList-Response,
    identify	 [2] IMPLICIT Identify-Response,
    rename	 [3] IMPLICIT Rename-Response,
    read	 [4] IMPLICIT Read-Response,
    write	 [5] IMPLICIT Write-Response,
    getVariableAccessAttributes	 [6] IMPLICIT GetVariableAccessAttributes-Response,
    defineNamedVariable	 [7] IMPLICIT DefineNamedVariable-Response,
    defineScatteredAccess	 [8] IMPLICIT DefineScatteredAccess-Response,
    getScatteredAccessAttributes	 [9] IMPLICIT GetScatteredAccessAttributes-Response,
    deleteVariableAccess	 [10] IMPLICIT DeleteVariableAccess-Response,
    defineNamedVariableList	 [11] IMPLICIT DefineNamedVariableList-Response,
    getNamedVariableListAttributes	 [12] IMPLICIT GetNamedVariableListAttributes-Response,
    deleteNamedVariableList	 [13] IMPLICIT DeleteNamedVariableList-Response,
    defineNamedType	 [14] IMPLICIT DefineNamedType-Response,
    getNamedTypeAttributes	 [15] IMPLICIT GetNamedTypeAttributes-Response,
    deleteNamedType	 [16] IMPLICIT DeleteNamedType-Response,
    input	 [17] IMPLICIT Input-Response,
    output	 [18] IMPLICIT Output-Response,
    takeControl	 [19] TakeControl-Response,
    relinquishControl	 [20] IMPLICIT RelinquishControl-Response,
    defineSemaphore	 [21] IMPLICIT DefineSemaphore-Response,
    deleteSemaphore	 [22] IMPLICIT DeleteSemaphore-Response,
    reportSemaphoreStatus	 [23] IMPLICIT ReportSemaphoreStatus-Response,
    reportPoolSemaphoreStatus	 [24] IMPLICIT ReportPoolSemaphoreStatus-Response,
    reportSemaphoreEntryStatus	 [25] IMPLICIT ReportSemaphoreEntryStatus-Response,
    initiateDownloadSequence	 [26] IMPLICIT InitiateDownloadSequence-Response,
    downloadSegment	 [27] IMPLICIT DownloadSegment-Response,
    terminateDownloadSequence	 [28] IMPLICIT TerminateDownloadSequence-Response,
    initiateUploadSequence	 [29] IMPLICIT InitiateUploadSequence-Response,
    uploadSegment	 [30] IMPLICIT UploadSegment-Response,
    terminateUploadSequence	 [31] IMPLICIT TerminateUploadSequence-Response,
    requestDomainDownload	 [32] IMPLICIT RequestDomainDownload-Response,
    requestDomainUpload	 [33] IMPLICIT RequestDomainUpload-Response,
    loadDomainContent	 [34] IMPLICIT LoadDomainContent-Response,
    storeDomainContent	 [35] IMPLICIT StoreDomainContent-Response,
    deleteDomain	 [36] IMPLICIT DeleteDomain-Response,
    getDomainAttributes	 [37] IMPLICIT GetDomainAttributes-Response,
    createProgramInvocation	 [38] IMPLICIT CreateProgramInvocation-Response,
    deleteProgramInvocation	 [39] IMPLICIT DeleteProgramInvocation-Response,
    start	 [40] IMPLICIT Start-Response,
    stop	 [41] IMPLICIT Stop-Response,
    resume	 [42] IMPLICIT Resume-Response,
    reset	 [43] IMPLICIT Reset-Response,
    kill	 [44] IMPLICIT Kill-Response,
    getProgramInvocationAttributes	 [45] IMPLICIT GetProgramInvocationAttributes-Response,
    obtainFile	 [46] IMPLICIT ObtainFile-Response,
    defineEventCondition	 [47] IMPLICIT DefineEventCondition-Response,
    deleteEventCondition	 [48] IMPLICIT DeleteEventCondition-Response,
    getEventConditionAttributes	 [49] IMPLICIT GetEventConditionAttributes-Response,
    reportEventConditionStatus	 [50] IMPLICIT ReportEventConditionStatus-Response,
    alterEventConditionMonitoring	 [51] IMPLICIT AlterEventConditionMonitoring-Response,
    triggerEvent	 [52] IMPLICIT TriggerEvent-Response,
    defineEventAction	 [53] IMPLICIT DefineEventAction-Response,
    deleteEventAction	 [54] IMPLICIT DeleteEventAction-Response,
    getEventActionAttributes	 [55] IMPLICIT GetEventActionAttributes-Response,
    reportEventActionStatus	 [56] IMPLICIT ReportEventActionStatus-Response,
    defineEventEnrollment	 [57] IMPLICIT DefineEventEnrollment-Response,
    deleteEventEnrollment	 [58] IMPLICIT DeleteEventEnrollment-Response,
    alterEventEnrollment	 [59] IMPLICIT AlterEventEnrollment-Response,
    reportEventEnrollmentStatus	 [60] IMPLICIT ReportEventEnrollmentStatus-Response,
    getEventEnrollmentAttributes	 [61] IMPLICIT GetEventEnrollmentAttributes-Response,
    acknowledgeEventNotification	 [62] IMPLICIT AcknowledgeEventNotification-Response,
    getAlarmSummary	 [63] IMPLICIT GetAlarmSummary-Response,
    getAlarmEnrollmentSummary	 [64] IMPLICIT GetAlarmEnrollmentSummary-Response,
    readJournal	 [65] IMPLICIT ReadJournal-Response,
    writeJournal	 [66] IMPLICIT WriteJournal-Response,
    initializeJournal	 [67] IMPLICIT InitializeJournal-Response,
    reportJournalStatus	 [68] IMPLICIT ReportJournalStatus-Response,
    createJournal	 [69] IMPLICIT CreateJournal-Response,
    deleteJournal	 [70] IMPLICIT DeleteJournal-Response,
    getCapabilityList	 [71] IMPLICIT GetCapabilityList-Response,
    fileOpen	 [72] IMPLICIT FileOpen-Response,
    fileRead	 [73] IMPLICIT FileRead-Response,
    fileClose	 [74] IMPLICIT FileClose-Response,
    fileRename	 [75] IMPLICIT FileRename-Response,
    fileDelete	 [76] IMPLICIT FileDelete-Response,
    fileDirectory	 [77] IMPLICIT FileDirectory-Response,
    additionalService	 [78] AdditionalService-Response,
    getDataExchangeAttributes	 [80] GetDataExchangeAttributes-Response,
    exchangeData	 [81] IMPLICIT ExchangeData-Response,
    defineAccessControlList	 [82] IMPLICIT DefineAccessControlList-Response,
    getAccessControlListAttributes	 [83] IMPLICIT GetAccessControlListAttributes-Response,
    reportAccessControlledObjects	 [84] IMPLICIT ReportAccessControlledObjects-Response,
    deleteAccessControlList	 [85] IMPLICIT DeleteAccessControlList-Response,
    changeAccessControl	 [86] IMPLICIT ChangeAccessControl-Response
}

AdditionalService-Response ::= CHOICE {
    vMDStop	 [0] IMPLICIT VMDStop-Response,
    vMDReset	 [1] IMPLICIT VMDReset-Response,
    select	 [2] IMPLICIT Select-Response,
    alterPI	 [3] IMPLICIT AlterProgramInvocationAttributes-Response,
    initiateUCLoad	 [4] IMPLICIT InitiateUnitControlLoad-Response,
    uCLoad	 [5] IMPLICIT UnitControlLoadSegment-Response,
    uCUpload	 [6] IMPLICIT UnitControlUpload-Response,
    startUC	 [7] IMPLICIT StartUnitControl-Response,
    stopUC	 [8] IMPLICIT StopUnitControl-Response,
    createUC	 [9] IMPLICIT CreateUnitControl-Response,
    addToUC	 [10] IMPLICIT AddToUnitControl-Response,
    removeFromUC	 [11] IMPLICIT RemoveFromUnitControl-Response,
    getUCAttributes	 [12] IMPLICIT GetUnitControlAttributes-Response,
    loadUCFromFile	 [13] IMPLICIT LoadUnitControlFromFile-Response,
    storeUCToFile	 [14] IMPLICIT StoreUnitControlToFile-Response,
    deleteUC	 [15] IMPLICIT DeleteUnitControl-Response,
    defineECL	 [16] IMPLICIT DefineEventConditionList-Response,
    deleteECL	 [17] IMPLICIT DeleteEventConditionList-Response,
    addECLReference	 [18] IMPLICIT AddEventConditionListReference-Response,
    removeECLReference	 [19] IMPLICIT RemoveEventConditionListReference-Response,
    getECLAttributes	 [20] IMPLICIT GetEventConditionListAttributes-Response,
    reportECLStatus	 [21] IMPLICIT ReportEventConditionListStatus-Response,
    alterECLMonitoring	 [22] IMPLICIT AlterEventConditionListMonitoring-Response
}

Response-Detail ::= CHOICE {
    otherRequests	 NULL,
    status	 [0] CS-Status-Response,
    getProgramInvocationAttributes	 [45] IMPLICIT CS-GetProgramInvocationAttributes-Response,
    getEventConditionAttributes	 [49] IMPLICIT CS-GetEventConditionAttributes-Response
}

ServiceError ::= SEQUENCE {
    errorClass	 [0] CHOICE {
        vmd-state	 [0] IMPLICIT INTEGER {
            other(0),
            vmd-state-conflict(1),
            vmd-operational-problem(2),
            domain-transfer-problem(3),
            state-machine-id-invalid(4)
        } (0..4),
        application-reference	 [1] IMPLICIT INTEGER {
            other(0),
            application-unreachable(1),
            connection-lost(2),
            application-reference-invalid(3),
            context-unsupported(4)
        } (0..4),
        definition	 [2] IMPLICIT INTEGER {
            other(0),
            object-undefined(1),
            invalid-address(2),
            type-unsupported(3),
            type-inconsistent(4),
            object-exists(5),
            object-attribute-inconsistent(6)
        } (0..6),
        resource	 [3] IMPLICIT INTEGER {
            other(0),
            memory-unavailable(1),
            processor-resource-unavailable(2),
            mass-storage-unavailable(3),
            capability-unavailable(4),
            capability-unknown(5)
        } (0..5),
        service	 [4] IMPLICIT INTEGER {
            other(0),
            primitives-out-of-sequence(1),
            object-state-conflict(2),
            pdu-size(3), -- added by IEC61850 8-1
            continuation-invalid(4),
            object-constraint-conflict(5)
        } (0..5),
        service-preempt	 [5] IMPLICIT INTEGER {
            other(0),
            timeout(1),
            deadlock(2),
            cancel(3)
        } (0..3),
        time-resolution	 [6] IMPLICIT INTEGER {
            other(0),
            unsupportable-time-resolution(1)
        } (0..1),
        access	 [7] IMPLICIT INTEGER {
            other(0),
            object-access-unsupported(1),
            object-non-existent(2),
            object-access-denied(3),
            object-invalidated(4)
        } (0..4),
        initiate	 [8] IMPLICIT INTEGER {
            other(0),
            max-services-outstanding-calling-insufficient(3),
            max-services-outstanding-called-insufficient(4),
            service-CBB-insufficient(5),
            parameter-CBB-insufficient(6),
            nesting-level-insufficient(7)
        } (0..7),
        conclude	 [9] IMPLICIT INTEGER {
            other(0),
            further-communication-required(1)
        } (0..1),
        cancel	 [10] IMPLICIT INTEGER {
            other(0),
            invoke-id-unknown(1),
            cancel-not-possible(2)
        } (0..2),
        file	 [11] IMPLICIT INTEGER {
            other(0),
            filename-ambiguous(1),
            file-busy(2),
            filename-syntax-error(3),
            content-type-invalid(4),
            position-invalid(5),
            file-access-denied(6),
            file-non-existent(7),
            duplicate-filename(8),
            insufficient-space-in-filestore(9)
        } (0..9),
        others	 [12] IMPLICIT INTEGER
    },
    additionalCode	 [1] IMPLICIT INTEGER OPTIONAL,
    additionalDescription	 [2] IMPLICIT VisibleString OPTIONAL,
    serviceSpecificInfo	 [3] CHOICE {
        obtainFile	 [0] IMPLICIT ObtainFile-Error,
        start	 [1] IMPLICIT Start-Error,
        stop	 [2] IMPLICIT Stop-Error,
        resume	 [3] IMPLICIT Resume-Error,
        reset	 [4] IMPLICIT Reset-Error,
        deleteVariableAccess	 [5] IMPLICIT DeleteVariableAccess-Error,
        deleteNamedVariableList	 [6] IMPLICIT DeleteNamedVariableList-Error,
        deleteNamedType	 [7] IMPLICIT DeleteNamedType-Error,
        defineEventEnrollment-Error	 [8] DefineEventEnrollment-Error,
        fileRename	 [9] IMPLICIT FileRename-Error,
        additionalService	 [10] AdditionalService-Error,
        changeAccessControl	 [11] IMPLICIT ChangeAccessControl-Error
    } OPTIONAL
}

AdditionalService-Error ::= CHOICE {
    defineEcl	 [0] DefineEventConditionList-Error,
    addECLReference	 [1] AddEventConditionListReference-Error,
    removeECLReference	 [2] RemoveEventConditionListReference-Error,
    initiateUC	 [3] InitiateUnitControl-Error,
    startUC	 [4] IMPLICIT StartUnitControl-Error,
    stopUC	 [5] IMPLICIT StopUnitControl-Error,
    deleteUC	 [6] DeleteUnitControl-Error,
    loadUCFromFile	 [7] LoadUnitControlFromFile-Error
}

Initiate-RequestPDU ::= SEQUENCE {
    localDetailCalling	 [0] IMPLICIT Integer32 OPTIONAL,
    proposedMaxServOutstandingCalling	 [1] IMPLICIT Integer16,
    proposedMaxServOutstandingCalled	 [2] IMPLICIT Integer16,
    proposedDataStructureNestingLevel	 [3] IMPLICIT Integer8 OPTIONAL,
    initRequestDetail	 [4] IMPLICIT SEQUENCE {
        proposedVersionNumber	 [0] IMPLICIT Integer16,
        proposedParameterCBB	 [1] IMPLICIT ParameterSupportOptions,
        servicesSupportedCalling	 [2] IMPLICIT ServiceSupportOptions,
-- IF (csr cspi)
        additionalSupportedCalling	 [3] IMPLICIT AdditionalSupportOptions OPTIONAL,
        additionalCbbSupportedCalling	 [4] IMPLICIT AdditionalCBBOptions OPTIONAL,
-- ENDIF
-- IF (cspi)
        privilegeClassIdentityCalling	 [5] IMPLICIT VisibleString OPTIONAL
-- ENDIF
    }
}

Initiate-ResponsePDU ::= SEQUENCE {
    localDetailCalled	 [0] IMPLICIT Integer32 OPTIONAL,
    negotiatedMaxServOutstandingCalling	 [1] IMPLICIT Integer16,
    negotiatedMaxServOutstandingCalled	 [2] IMPLICIT Integer16,
    negotiatedDataStructureNestingLevel	 [3] IMPLICIT Integer8 OPTIONAL,
    initResponseDetail	 [4] IMPLICIT SEQUENCE {
        negotiatedVersionNumber	 [0] IMPLICIT Integer16,
        negotiatedParameterCBB	 [1] IMPLICIT ParameterSupportOptions,
        servicesSupportedCalled	 [2] IMPLICIT ServiceSupportOptions,
-- IF (csr cspi)
        additionalSupportedCalled	 [3] IMPLICIT AdditionalSupportOptions OPTIONAL,
        additionalCbbSupportedCalled	 [4] IMPLICIT AdditionalCBBOptions OPTIONAL,
-- ENDIF
-- IF (cspi)
        privilegeClassIdentityCalled	 [5] IMPLICIT VisibleString OPTIONAL
-- ENDIF
    }
}

Initiate-ErrorPDU ::= ServiceError

Conclude-RequestPDU ::= NULL

Conclude-ResponsePDU ::= NULL

Conclude-ErrorPDU ::= ServiceError

Cancel-RequestPDU ::= Unsigned32

Cancel-ResponsePDU ::= Unsigned32

Cancel-ErrorPDU ::= SEQUENCE {
    originalInvokeID	 [0] IMPLICIT Unsigned32,
    serviceError	 [1] IMPLICIT ServiceError
}

RejectPDU ::= SEQUENCE {
    originalInvokeID	 [0] IMPLICIT Unsigned32 OPTIONAL,
    rejectReason	 CHOICE {
        confirmed-requestPDU	 [1] IMPLICIT INTEGER {
            other(0),
            unrecognized-service(1),
            unrecognized-modifier(2),
            invalid-invokeID(3),
            invalid-argument(4),
            invalid-modifier(5),
            max-serv-outstanding-exceeded(6),
            max-recursion-exceeded(8),
            value-out-of-range(9)
        } (0..9),
        confirmed-responsePDU	 [2] IMPLICIT INTEGER {
            other(0),
            unrecognized-service(1),
            invalid-invokeID(2),
            invalid-result(3),
            max-recursion-exceeded(5),
            value-out-of-range(6)
        } (0..6),
        confirmed-errorPDU	 [3] IMPLICIT INTEGER {
            other(0),
            unrecognized-service(1),
            invalid-invokeID(2),
            invalid-serviceError(3),
            value-out-of-range(4)
        } (0..4),
        unconfirmedPDU	 [4] IMPLICIT INTEGER {
            other(0),
            unrecognized-service(1),
            invalid-argument(2),
            max-recursion-exceeded(3),
            value-out-of-range(4)
        } (0..4),
        pdu-error	 [5] IMPLICIT INTEGER {
            unknown-pdu-type(0),
            invalid-pdu(1),
            illegal-acse-mapping(2)
        },
        cancel-requestPDU	 [6] IMPLICIT INTEGER {
            other(0),
            invalid-invokeID(1)
        } (0..1),
        cancel-responsePDU	 [7] IMPLICIT INTEGER {
            other(0),
            invalid-invokeID(1)
        } (0..1),
        cancel-errorPDU	 [8] IMPLICIT INTEGER {
            other(0),
            invalid-invokeID(1),
            invalid-serviceError(2),
            value-out-of-range(3)
        } (0..3),
        conclude-requestPDU	 [9] IMPLICIT INTEGER {
            other(0),
            invalid-argument(1)
        } (0..1),
        conclude-responsePDU	 [10] IMPLICIT INTEGER {
            other(0),
            invalid-result(1)
        } (0..1),
        conclude-errorPDU	 [11] IMPLICIT INTEGER {
            other(0),
            invalid-serviceError(1),
            value-out-of-range(2)
        } (0..2)
    }
}

DefineAccessControlList-Request ::= SEQUENCE {
    accessControlListName	 [0] IMPLICIT Identifier,
    accessControlListElements	 [1] IMPLICIT SEQUENCE {
        readAccessCondition	 [0] AccessCondition OPTIONAL,
        storeAccessCondition	 [1] AccessCondition OPTIONAL,
        writeAccessCondition	 [2] AccessCondition OPTIONAL,
        loadAccessCondition	 [3] AccessCondition OPTIONAL,
        executeAccessCondition	 [4] AccessCondition OPTIONAL,
        deleteAccessCondition	 [5] AccessCondition OPTIONAL,
        editAccessCondition	 [6] AccessCondition OPTIONAL
    }
}

DefineAccessControlList-Response ::= NULL

GetAccessControlListAttributes-Request ::= CHOICE {
    accessControlListName	 [0] IMPLICIT Identifier,
    vMD	 [1] IMPLICIT NULL,
    namedObject	 [2] IMPLICIT SEQUENCE {
        objectClass	 [0] ObjectClass,
        objectName	 [1] ObjectName
    }
}

GetAccessControlListAttributes-Response ::= SEQUENCE {
    name	 [0] Identifier,
    accessControlListElements	 [1] IMPLICIT SEQUENCE {
        readAccessCondition	 [0] AccessCondition OPTIONAL,
        storeAccessCondition	 [1] AccessCondition OPTIONAL,
        writeAccessCondition	 [2] AccessCondition OPTIONAL,
        loadAccessCondition	 [3] AccessCondition OPTIONAL,
        executeAccessCondition	 [4] AccessCondition OPTIONAL,
        deleteAccessCondition	 [5] AccessCondition OPTIONAL,
        editAccessCondition	 [6] AccessCondition OPTIONAL
    },
    vMDuse	 [2] IMPLICIT BOOLEAN,
    references	 [3] IMPLICIT SEQUENCE OF SEQUENCE {
            objectClass	 [0] ObjectClass,
            objectCount	 [1] IMPLICIT INTEGER
        },
    accessControlList	 [4] IMPLICIT Identifier OPTIONAL
}

ReportAccessControlledObjects-Request ::= SEQUENCE {
    accessControlList	 [0] IMPLICIT Identifier,
    objectClass	 [1] ObjectClass,
    continueAfter	 [2] ObjectName OPTIONAL
}

ReportAccessControlledObjects-Response ::= SEQUENCE {
    listOfNames	 [0] IMPLICIT SEQUENCE OF ObjectName,
    moreFollows	 [1] IMPLICIT BOOLEAN DEFAULT FALSE
}

DeleteAccessControlList-Request ::= Identifier

DeleteAccessControlList-Response ::= NULL

ChangeAccessControl-Request ::= SEQUENCE {
    scopeOfChange	 CHOICE {
        vMDOnly	 [0] IMPLICIT NULL,
        listOfObjects	 [1] IMPLICIT SEQUENCE {
            objectClass	 [0] ObjectClass,
            objectScope	 [1] CHOICE {
                specific	 [0] IMPLICIT SEQUENCE OF ObjectName,
                aa-specific	 [1] IMPLICIT NULL,
                domain	 [2] IMPLICIT Identifier,
                vmd	 [3] IMPLICIT NULL
            }
        }
    },
    accessControlListName	 [2] IMPLICIT Identifier
}

ChangeAccessControl-Response ::= SEQUENCE {
    numberMatched	 [0] IMPLICIT Unsigned32,
    numberChanged	 [1] IMPLICIT Unsigned32
}

ChangeAccessControl-Error ::= Unsigned32

StatusResponse ::= SEQUENCE {
    vmdLogicalStatus	 [0] IMPLICIT INTEGER {
        state-changes-allowed(0),
        no-state-changes-allowed(1),
        limited-services-permitted(2),
        support-services-allowed(3)
    } (0..3),
    vmdPhysicalStatus	 [1] IMPLICIT INTEGER {
        operational(0),
        partially-operational(1),
        inoperable(2),
        needs-commissioning(3)
    } (0..3),
    localDetail	 [2] IMPLICIT BIT STRING (SIZE(0..128)) OPTIONAL
}

CS-Status-Response ::= CHOICE {
    fullResponse	 SEQUENCE {
        operationState	 [0] IMPLICIT OperationState,
        extendedStatus	 [1] IMPLICIT ExtendedStatus,
        extendedStatusMask	 [2] IMPLICIT ExtendedStatus DEFAULT '1111'B,
        selectedProgramInvocation	 CHOICE {
            programInvocation	 [3] IMPLICIT Identifier,
            noneSelected	 [4] IMPLICIT NULL
        }
    },
    noExtraResponse	 NULL
}

OperationState ::= INTEGER {
    idle(0),
    loaded(1),
    ready(2),
    executing(3),
    motion-paused(4),
    manualInterventionRequired(5)
} (0..5)

ExtendedStatus ::= BIT STRING {
    safetyInterlocksViolated(0),
    anyPhysicalResourcePowerOn(1),
    allPhysicalResourcesCalibrated(2),
    localControl(3)
} -- (SIZE(4))

Status-Request ::= BOOLEAN

Status-Response ::= StatusResponse

UnsolicitedStatus ::= StatusResponse

GetNameList-Request ::= SEQUENCE {
    objectClass	 [0] ObjectClass,
    objectScope	 [1] CHOICE {
        vmdSpecific	 [0] IMPLICIT NULL,
        domainSpecific	 [1] IMPLICIT Identifier,
        aaSpecific	 [2] IMPLICIT NULL
    },
    continueAfter	 [2] IMPLICIT Identifier OPTIONAL
}

GetNameList-Response ::= SEQUENCE {
    listOfIdentifier	 [0] IMPLICIT SEQUENCE OF Identifier,
    moreFollows	 [1] IMPLICIT BOOLEAN DEFAULT TRUE
}

Identify-Request ::= NULL

Identify-Response ::= SEQUENCE {
    vendorName	 [0] IMPLICIT MMSString,
    modelName	 [1] IMPLICIT MMSString,
    revision	 [2] IMPLICIT MMSString,
    listOfAbstractSyntaxes	 [3] IMPLICIT SEQUENCE OF OBJECT IDENTIFIER OPTIONAL
}

Rename-Request ::= SEQUENCE {
    objectClass	 [0] ObjectClass,
    currentName	 [1] ObjectName,
    newIdentifier	 [2] IMPLICIT Identifier
}

Rename-Response ::= NULL

GetCapabilityList-Request ::= SEQUENCE {
    continueAfter	 MMSString OPTIONAL
}

GetCapabilityList-Response ::= SEQUENCE {
    listOfCapabilities	 [0] IMPLICIT SEQUENCE OF MMSString,
    moreFollows	 [1] IMPLICIT BOOLEAN DEFAULT TRUE
}

VMDStop-Request ::= NULL

VMDStop-Response ::= NULL

VMDReset-Request ::= BOOLEAN

VMDReset-Response ::= StatusResponse

InitiateDownloadSequence-Request ::= SEQUENCE {
    domainName	 [0] IMPLICIT Identifier,
    listOfCapabilities	 [1] IMPLICIT SEQUENCE OF MMSString,
    sharable	 [2] IMPLICIT BOOLEAN
}

InitiateDownloadSequence-Response ::= NULL

DownloadSegment-Request ::= Identifier

DownloadSegment-Response ::= SEQUENCE {
    loadData	 LoadData,
    moreFollows	 [1] IMPLICIT BOOLEAN DEFAULT TRUE
}

LoadData ::= CHOICE {
    non-coded	 [0] IMPLICIT OCTET STRING,
    coded	 EXTERNAL,
    embedded	 EMBEDDED-PDV
}

TerminateDownloadSequence-Request ::= SEQUENCE {
    domainName	 [0] IMPLICIT Identifier,
    discard	 [1] IMPLICIT ServiceError OPTIONAL
}

TerminateDownloadSequence-Response ::= NULL

InitiateUploadSequence-Request ::= Identifier

InitiateUploadSequence-Response ::= SEQUENCE {
    ulsmID	 [0] IMPLICIT Integer32,
    listOfCapabilities	 [1] IMPLICIT SEQUENCE OF MMSString
}

UploadSegment-Request ::= Integer32

UploadSegment-Response ::= SEQUENCE {
    loadData	 LoadData,
    moreFollows	 [1] IMPLICIT BOOLEAN DEFAULT TRUE
}

TerminateUploadSequence-Request ::= Integer32

TerminateUploadSequence-Response ::= NULL

RequestDomainDownload-Request ::= SEQUENCE {
    domainName	 [0] IMPLICIT Identifier,
    listOfCapabilities	 [1] IMPLICIT SEQUENCE OF MMSString OPTIONAL,
    sharable	 [2] IMPLICIT BOOLEAN,
    fileName	 [4] IMPLICIT FileName
}

RequestDomainDownload-Response ::= NULL

RequestDomainUpload-Request ::= SEQUENCE {
    domainName	 [0] IMPLICIT Identifier,
    fileName	 [1] IMPLICIT FileName
}

RequestDomainUpload-Response ::= NULL

LoadDomainContent-Request ::= SEQUENCE {
    domainName	 [0] IMPLICIT Identifier,
    listOfCapabilities	 [1] IMPLICIT SEQUENCE OF MMSString OPTIONAL,
    sharable	 [2] IMPLICIT BOOLEAN,
    fileName	 [4] IMPLICIT FileName,
    thirdParty	 [5] IMPLICIT ApplicationReference OPTIONAL
}

LoadDomainContent-Response ::= NULL

StoreDomainContent-Request ::= SEQUENCE {
    domainName	 [0] IMPLICIT Identifier,
    fileName	 [1] IMPLICIT FileName,
    thirdParty	 [2] IMPLICIT ApplicationReference OPTIONAL
}

StoreDomainContent-Response ::= NULL

DeleteDomain-Request ::= Identifier

DeleteDomain-Response ::= NULL

GetDomainAttributes-Request ::= Identifier

GetDomainAttributes-Response ::= SEQUENCE {
    listOfCapabilities	 [0] IMPLICIT SEQUENCE OF MMSString,
    state	 [1] IMPLICIT DomainState,
    mmsDeletable	 [2] IMPLICIT BOOLEAN,
    sharable	 [3] IMPLICIT BOOLEAN,
    listOfProgramInvocations	 [4] IMPLICIT SEQUENCE OF Identifier,
    uploadInProgress	 [5] IMPLICIT Integer8,
    accessControlList	 [6] IMPLICIT Identifier OPTIONAL
}

CreateProgramInvocation-Request ::= SEQUENCE {
    programInvocationName	 [0] IMPLICIT Identifier,
    listOfDomainNames	 [1] IMPLICIT SEQUENCE OF Identifier,
    reusable	 [2] IMPLICIT BOOLEAN DEFAULT TRUE,
    monitorType	 [3] IMPLICIT BOOLEAN OPTIONAL
}

CreateProgramInvocation-Response ::= NULL

CS-CreateProgramInvocation-Request ::= INTEGER {
    normal(0),
    controlling(1),
    controlled(2)
} (0..2)

DeleteProgramInvocation-Request ::= Identifier

DeleteProgramInvocation-Response ::= NULL

Start-Request ::= SEQUENCE {
    programInvocationName	 [0] IMPLICIT Identifier,
    executionArgument	 CHOICE {
        simpleString	 [1] IMPLICIT MMSString,
        encodedString	 EXTERNAL,
        embeddedString	 EMBEDDED-PDV
    } OPTIONAL
}

Start-Response ::= NULL

Start-Error ::= ProgramInvocationState

CS-Start-Request ::= [0] CHOICE {
    normal	 NULL,
    controlling	 SEQUENCE {
        startLocation	 [0] IMPLICIT VisibleString OPTIONAL,
        startCount	 [1] StartCount DEFAULT {cycleCount: 1}
    }
}

StartCount ::= CHOICE {
    noLimit	 [0] IMPLICIT NULL,
    cycleCount	 [1] IMPLICIT INTEGER,
    stepCount	 [2] IMPLICIT INTEGER
}

Stop-Request ::= SEQUENCE {
    programInvocationName	 [0] IMPLICIT Identifier
}

Stop-Response ::= NULL

Stop-Error ::= ProgramInvocationState

Resume-Request ::= SEQUENCE {
    programInvocationName	 [0] IMPLICIT Identifier,
    executionArgument	 CHOICE {
        simpleString	 [1] IMPLICIT MMSString,
        encodedString	 EXTERNAL,
        enmbeddedString	 EMBEDDED-PDV
    } OPTIONAL
}

Resume-Response ::= NULL

Resume-Error ::= ProgramInvocationState

CS-Resume-Request ::= [0] CHOICE {
    normal	 NULL,
    controlling	 SEQUENCE {
        modeType	 CHOICE {
            continueMode	 [0] IMPLICIT NULL,
            changeMode	 [1] StartCount
        }
    }
}

Reset-Request ::= SEQUENCE {
    programInvocationName	 [0] IMPLICIT Identifier
}

Reset-Response ::= NULL

Reset-Error ::= ProgramInvocationState

Kill-Request ::= SEQUENCE {
    programInvocationName	 [0] IMPLICIT Identifier
}

Kill-Response ::= NULL

GetProgramInvocationAttributes-Request ::= Identifier

GetProgramInvocationAttributes-Response ::= SEQUENCE {
    state	 [0] IMPLICIT ProgramInvocationState,
    listOfDomainNames	 [1] IMPLICIT SEQUENCE OF Identifier,
    mmsDeletable	 [2] IMPLICIT BOOLEAN,
    reusable	 [3] IMPLICIT BOOLEAN,
    monitor	 [4] IMPLICIT BOOLEAN,
    executionArgument	 CHOICE {
        simpleString	 [5] IMPLICIT MMSString,
        encodedString	 EXTERNAL,
        enmbeddedString	 EMBEDDED-PDV
    },
    accessControlList	 [6] IMPLICIT Identifier OPTIONAL
}

CS-GetProgramInvocationAttributes-Response ::= SEQUENCE {
    errorCode	 [0] IMPLICIT INTEGER,
    control	 [1] CHOICE {
        controlling	 [0] IMPLICIT SEQUENCE {
            controlledPI	 [0] IMPLICIT SEQUENCE OF Identifier,
            programLocation	 [1] IMPLICIT VisibleString OPTIONAL,
            runningMode	 [2] CHOICE {
                freeRunning	 [0] IMPLICIT NULL,
                cycleLimited	 [1] IMPLICIT INTEGER,
                stepLimited	 [2] IMPLICIT INTEGER
            }
        },
        controlled	 [1] CHOICE {
            controllingPI	 [0] IMPLICIT Identifier,
            none	 [1] IMPLICIT NULL
        },
        normal	 [2] IMPLICIT NULL
    }
}

Select-Request ::= SEQUENCE {
    controlling	 [0] IMPLICIT Identifier OPTIONAL,
    controlled	 [1] IMPLICIT SEQUENCE OF Identifier OPTIONAL
}

Select-Response ::= NULL

AlterProgramInvocationAttributes-Request ::= SEQUENCE {
    programInvocation	 [0] IMPLICIT Identifier,
    startCount	 [1] StartCount DEFAULT {cycleCount: 1}
}

AlterProgramInvocationAttributes-Response ::= NULL

ControlElement ::= CHOICE {
    beginDomainDef	 [0] SEQUENCE {
        domainName	 [1] IMPLICIT Identifier,
        capabilities	 [2] IMPLICIT SEQUENCE OF MMSString,
        sharable	 [3] IMPLICIT BOOLEAN,
        loadData	 [4] LoadData OPTIONAL
    },
    continueDomainDef	 [1] SEQUENCE {
        domainName	 [1] IMPLICIT Identifier,
        loadData	 [3] LoadData
    },
    endDomainDef	 [2] IMPLICIT Identifier,
    piDefinition	 [3] IMPLICIT SEQUENCE {
        piName	 [0] IMPLICIT Identifier,
        listOfDomains	 [1] IMPLICIT SEQUENCE OF Identifier,
        reusable	 [2] IMPLICIT BOOLEAN DEFAULT TRUE,
        monitorType	 [3] IMPLICIT BOOLEAN OPTIONAL,
        pIState	 [4] IMPLICIT ProgramInvocationState OPTIONAL
    }
}

InitiateUnitControlLoad-Request ::= Identifier

InitiateUnitControlLoad-Response ::= NULL

InitiateUnitControl-Error ::= CHOICE {
    domain	 [0] IMPLICIT Identifier,
    programInvocation	 [1] IMPLICIT Identifier
}

UnitControlLoadSegment-Request ::= Identifier

UnitControlLoadSegment-Response ::= SEQUENCE {
    controlElements	 [0] IMPLICIT SEQUENCE OF ControlElement,
    moreFollows	 [1] IMPLICIT BOOLEAN DEFAULT TRUE
}

UnitControlUpload-Request ::= SEQUENCE {
    unitControlName	 [0] IMPLICIT Identifier,
    continueAfter	 CHOICE {
        domain	 [1] IMPLICIT Identifier,
        ulsmID	 [2] IMPLICIT INTEGER,
        programInvocation	 [3] IMPLICIT Identifier
    } OPTIONAL
}

UnitControlUpload-Response ::= SEQUENCE {
    controlElements	 [0] IMPLICIT SEQUENCE OF ControlElement,
    nextElement	 CHOICE {
        domain	 [1] IMPLICIT Identifier,
        ulsmID	 [2] IMPLICIT INTEGER,
        programInvocation	 [3] IMPLICIT Identifier
    } OPTIONAL
}

StartUnitControl-Request ::= SEQUENCE {
    unitControlName	 [0] IMPLICIT Identifier,
    executionArgument	 CHOICE {
        simpleString	 [1] IMPLICIT MMSString,
        encodedString	 EXTERNAL,
        enmbeddedString	 EMBEDDED-PDV
    } OPTIONAL
}

StartUnitControl-Response ::= NULL

StartUnitControl-Error ::= SEQUENCE {
    programInvocationName	 [0] IMPLICIT Identifier,
    programInvocationState	 [1] IMPLICIT ProgramInvocationState
}

StopUnitControl-Request ::= Identifier

StopUnitControl-Response ::= NULL

StopUnitControl-Error ::= SEQUENCE {
    programInvocationName	 [0] IMPLICIT Identifier,
    programInvocationState	 [1] IMPLICIT ProgramInvocationState
}

CreateUnitControl-Request ::= SEQUENCE {
    unitControl	 [0] IMPLICIT Identifier,
    domains	 [1] IMPLICIT SEQUENCE OF Identifier,
    programInvocations	 [2] IMPLICIT SEQUENCE OF Identifier
}

CreateUnitControl-Response ::= NULL

AddToUnitControl-Request ::= SEQUENCE {
    unitControl	 [0] IMPLICIT Identifier,
    domains	 [1] IMPLICIT SEQUENCE OF Identifier,
    programInvocations	 [2] IMPLICIT SEQUENCE OF Identifier
}

AddToUnitControl-Response ::= NULL

RemoveFromUnitControl-Request ::= SEQUENCE {
    unitControl	 [0] IMPLICIT Identifier,
    domains	 [1] IMPLICIT SEQUENCE OF Identifier,
    programInvocations	 [2] IMPLICIT SEQUENCE OF Identifier
}

RemoveFromUnitControl-Response ::= NULL

GetUnitControlAttributes-Request ::= Identifier

GetUnitControlAttributes-Response ::= SEQUENCE {
    domains	 [0] IMPLICIT SEQUENCE OF Identifier,
    programInvocations	 [1] IMPLICIT SEQUENCE OF Identifier
}

LoadUnitControlFromFile-Request ::= SEQUENCE {
    unitControlName	 [0] IMPLICIT Identifier,
    fileName	 [1] IMPLICIT FileName,
    thirdParty	 [2] IMPLICIT ApplicationReference OPTIONAL
}

LoadUnitControlFromFile-Response ::= NULL

LoadUnitControlFromFile-Error ::= CHOICE {
    none	 [0] IMPLICIT NULL,
    domain	 [1] IMPLICIT Identifier,
    programInvocation	 [2] IMPLICIT Identifier
}

StoreUnitControlToFile-Request ::= SEQUENCE {
    unitControlName	 [0] IMPLICIT Identifier,
    fileName	 [1] IMPLICIT FileName,
    thirdParty	 [2] IMPLICIT ApplicationReference OPTIONAL
}

StoreUnitControlToFile-Response ::= NULL

DeleteUnitControl-Request ::= Identifier

DeleteUnitControl-Response ::= NULL

DeleteUnitControl-Error ::= CHOICE {
    domain	 [0] IMPLICIT Identifier,
    programInvocation	 [1] IMPLICIT Identifier
}

TypeSpecification ::= CHOICE {
    typeName	 [0] ObjectName,
    typeDescription	 TypeDescription
}

AlternateAccess ::= SEQUENCE OF CHOICE {
        unnamed	 AlternateAccessSelection,
        named	 [5] IMPLICIT SEQUENCE {
            componentName	 [0] IMPLICIT Identifier,
            access	 AlternateAccessSelection
        }
    }

AlternateAccessSelection ::= CHOICE {
    selectAlternateAccess	 [0] IMPLICIT SEQUENCE {
        accessSelection	 CHOICE {
            component	 [0] IMPLICIT Identifier,
            index	 [1] IMPLICIT Unsigned32,
            indexRange	 [2] IMPLICIT SEQUENCE {
                lowIndex	 [0] IMPLICIT Unsigned32,
                numberOfElements	 [1] IMPLICIT Unsigned32
            },
            allElements	 [3] IMPLICIT NULL
        },
        alternateAccess	 AlternateAccess
    },
    selectAccess	 CHOICE {
        component	 [1] IMPLICIT Identifier,
        index	 [2] IMPLICIT Unsigned32,
        indexRange	 [3] IMPLICIT SEQUENCE {
            lowIndex	 [0] IMPLICIT Unsigned32,
            numberOfElements	 [1] IMPLICIT Unsigned32
        },
        allElements	 [4] IMPLICIT NULL
    }
}

AccessResult ::= CHOICE {
    failure	 [0] IMPLICIT DataAccessError,
    success	 Data
}

Data ::= CHOICE {
    array	 [1] IMPLICIT SEQUENCE OF Data,
    structure	 [2] IMPLICIT SEQUENCE OF Data,
    boolean	 [3] IMPLICIT BOOLEAN,
    bit-string	 [4] IMPLICIT BIT STRING,
    integer	 [5] IMPLICIT INTEGER,
    unsigned	 [6] IMPLICIT INTEGER,
    floating-point	 [7] IMPLICIT FloatingPoint,
    octet-string	 [9] IMPLICIT OCTET STRING,
    visible-string	 [10] IMPLICIT VisibleString,
    generalized-time	 [11] IMPLICIT GeneralizedTime,
    binary-time	 [12] IMPLICIT TimeOfDay,
    bcd	 [13] IMPLICIT INTEGER,
    booleanArray	 [14] IMPLICIT BIT STRING,
    objId	 [15] IMPLICIT OBJECT IDENTIFIER,
    mMSString	 [16] IMPLICIT MMSString,
    utc-time    [17] IMPLICIT UtcTime
}

-- Added by IEC61850 8.1
UtcTime ::= OCTET STRING

FloatingPoint ::= OCTET STRING

DataAccessError ::= INTEGER {
    object-invalidated(0),
    hardware-fault(1),
    temporarily-unavailable(2),
    object-access-denied(3),
    object-undefined(4),
    invalid-address(5),
    type-unsupported(6),
    type-inconsistent(7),
    object-attribute-inconsistent(8),
    object-access-unsupported(9),
    object-non-existent(10),
    object-value-invalid(11)
} (0..11)

VariableAccessSpecification ::= CHOICE {
    listOfVariable	 [0] IMPLICIT SEQUENCE OF SEQUENCE {
            variableSpecification	 VariableSpecification,
            alternateAccess	 [5] IMPLICIT AlternateAccess OPTIONAL
        },
    variableListName	 [1] ObjectName
}

VariableSpecification ::= CHOICE {
    name	 [0] ObjectName,
    address	 [1] Address,
    variableDescription	 [2] IMPLICIT SEQUENCE {
        address	 Address,
        typeSpecification	 TypeSpecification
    },
    scatteredAccessDescription	 [3] IMPLICIT ScatteredAccessDescription,
    invalidated	 [4] IMPLICIT NULL
}

Read-Request ::= SEQUENCE {
    specificationWithResult	 [0] IMPLICIT BOOLEAN DEFAULT FALSE,
    variableAccessSpecification	 [1] VariableAccessSpecification
}

Read-Response ::= SEQUENCE {
    variableAccessSpecification	 [0] VariableAccessSpecification OPTIONAL,
    listOfAccessResult	 [1] IMPLICIT SEQUENCE OF AccessResult
}

Write-Response ::= SEQUENCE OF CHOICE {
        failure	 [0] IMPLICIT DataAccessError,
        success	 [1] IMPLICIT NULL
    }

Write-Request ::= SEQUENCE {
    variableAccessSpecification	 VariableAccessSpecification,
    listOfData	 [0] IMPLICIT SEQUENCE OF Data
}

InformationReport ::= SEQUENCE {
    variableAccessSpecification	 VariableAccessSpecification,
    listOfAccessResult	 [0] IMPLICIT SEQUENCE OF AccessResult
}

GetVariableAccessAttributes-Request ::= CHOICE {
    name	 [0] ObjectName,
    address	 [1] Address
}

GetVariableAccessAttributes-Response ::= SEQUENCE {
    mmsDeletable	 [0] IMPLICIT BOOLEAN,
    address	 [1] Address OPTIONAL,
    typeDescription	 [2] TypeDescription,
    accessControlList	 [3] IMPLICIT Identifier OPTIONAL,
    meaning	 [4] IMPLICIT VisibleString OPTIONAL
}

DefineNamedVariable-Request ::= SEQUENCE {
    variableName	 [0] ObjectName,
    address	 [1] Address,
    typeSpecification	 [2] TypeSpecification OPTIONAL
}

DefineNamedVariable-Response ::= NULL

DeleteVariableAccess-Request ::= SEQUENCE {
    scopeOfDelete	 [0] IMPLICIT INTEGER {
        specific(0),
        aa-specific(1),
        domain(2),
        vmd(3)
    } (0..3) DEFAULT specific,
    listOfName	 [1] IMPLICIT SEQUENCE OF ObjectName OPTIONAL,
    domainName	 [2] IMPLICIT Identifier OPTIONAL
}

DeleteVariableAccess-Response ::= SEQUENCE {
    numberMatched	 [0] IMPLICIT Unsigned32,
    numberDeleted	 [1] IMPLICIT Unsigned32
}

DeleteVariableAccess-Error ::= Unsigned32

DefineNamedVariableList-Request ::= SEQUENCE {
    variableListName	 ObjectName,
    listOfVariable	 [0] IMPLICIT SEQUENCE OF SEQUENCE {
            variableSpecification	 VariableSpecification,
            alternateAccess	 [5] IMPLICIT AlternateAccess OPTIONAL
        }
}

DefineNamedVariableList-Response ::= NULL

GetNamedVariableListAttributes-Request ::= ObjectName

GetNamedVariableListAttributes-Response ::= SEQUENCE {
    mmsDeletable	 [0] IMPLICIT BOOLEAN,
    listOfVariable	 [1] IMPLICIT SEQUENCE OF SEQUENCE {
            variableSpecification	 VariableSpecification,
            alternateAccess	 [5] IMPLICIT AlternateAccess OPTIONAL
        },
    accessControlList	 [2] IMPLICIT Identifier OPTIONAL
}

DeleteNamedVariableList-Response ::= SEQUENCE {
    numberMatched	 [0] IMPLICIT Unsigned32,
    numberDeleted	 [1] IMPLICIT Unsigned32
}

DeleteNamedVariableList-Request ::= SEQUENCE {
    scopeOfDelete	 [0] IMPLICIT INTEGER {
        specific(0),
        aa-specific(1),
        domain(2),
        vmd(3)
    } (0..3) DEFAULT specific,
    listOfVariableListName	 [1] IMPLICIT SEQUENCE OF ObjectName OPTIONAL,
    domainName	 [2] IMPLICIT Identifier OPTIONAL
}

DeleteNamedVariableList-Error ::= Unsigned32

DefineNamedType-Request ::= SEQUENCE {
    typeName	 ObjectName,
    typeSpecification	 TypeSpecification
}

DefineNamedType-Response ::= NULL

GetNamedTypeAttributes-Request ::= ObjectName

GetNamedTypeAttributes-Response ::= SEQUENCE {
    mmsDeletable	 [0] IMPLICIT BOOLEAN,
    typeSpecification	 TypeSpecification,
    accessControlList	 [1] IMPLICIT Identifier OPTIONAL,
    meaning	 [4] IMPLICIT VisibleString OPTIONAL
}

DeleteNamedType-Request ::= SEQUENCE {
    scopeOfDelete	 [0] IMPLICIT INTEGER {
        specific(0),
        aa-specific(1),
        domain(2),
        vmd(3)
    } (0..3) DEFAULT specific,
    listOfTypeName	 [1] IMPLICIT SEQUENCE OF ObjectName OPTIONAL,
    domainName	 [2] IMPLICIT Identifier OPTIONAL
}

DeleteNamedType-Response ::= SEQUENCE {
    numberMatched	 [0] IMPLICIT Unsigned32,
    numberDeleted	 [1] IMPLICIT Unsigned32
}

DeleteNamedType-Error ::= Unsigned32

ExchangeData-Request ::= SEQUENCE {
    dataExchangeName	 [0] ObjectName,
    listOfRequestData	 [1] IMPLICIT SEQUENCE OF Data
}

ExchangeData-Response ::= SEQUENCE {
    listOfResponseData	 [0] IMPLICIT SEQUENCE OF Data
}

GetDataExchangeAttributes-Request ::= ObjectName

GetDataExchangeAttributes-Response ::= SEQUENCE {
    inUse	 [0] IMPLICIT BOOLEAN,
    listOfRequestTypeDescriptions	 [1] IMPLICIT SEQUENCE OF TypeDescription,
    listOfResponseTypeDescriptions	 [2] IMPLICIT SEQUENCE OF TypeDescription,
    programInvocation	 [3] IMPLICIT Identifier OPTIONAL,
    accessControlList	 [4] IMPLICIT Identifier OPTIONAL
}

TakeControl-Request ::= SEQUENCE {
    semaphoreName	 [0] ObjectName,
    namedToken	 [1] IMPLICIT Identifier OPTIONAL,
    priority	 [2] IMPLICIT Priority DEFAULT normalPriority,
    acceptableDelay	 [3] IMPLICIT Unsigned32 OPTIONAL,
    controlTimeOut	 [4] IMPLICIT Unsigned32 OPTIONAL,
    abortOnTimeOut	 [5] IMPLICIT BOOLEAN OPTIONAL,
    relinquishIfConnectionLost	 [6] IMPLICIT BOOLEAN DEFAULT TRUE,
    applicationToPreempt	 [7] IMPLICIT ApplicationReference OPTIONAL
}

TakeControl-Response ::= CHOICE {
    noResult	 [0] IMPLICIT NULL,
    namedToken	 [1] IMPLICIT Identifier
}

RelinquishControl-Request ::= SEQUENCE {
    semaphoreName	 [0] ObjectName,
    namedToken	 [1] IMPLICIT Identifier OPTIONAL
}

RelinquishControl-Response ::= NULL

DefineSemaphore-Request ::= SEQUENCE {
    semaphoreName	 [0] ObjectName,
    numberOfTokens	 [1] IMPLICIT Unsigned16
}

DefineSemaphore-Response ::= NULL

DeleteSemaphore-Request ::= ObjectName

DeleteSemaphore-Response ::= NULL

ReportSemaphoreStatus-Request ::= ObjectName

ReportSemaphoreStatus-Response ::= SEQUENCE {
    mmsDeletable	 [0] IMPLICIT BOOLEAN,
    class	 [1] IMPLICIT INTEGER {
        token(0),
        pool(1)
    } (0..1),
    numberOfTokens	 [2] IMPLICIT Unsigned16,
    numberOfOwnedTokens	 [3] IMPLICIT Unsigned16,
    numberOfHungTokens	 [4] IMPLICIT Unsigned16,
    accessControlList	 [5] IMPLICIT Identifier OPTIONAL
}

ReportPoolSemaphoreStatus-Request ::= SEQUENCE {
    semaphoreName	 [0] ObjectName,
    nameToStartAfter	 [1] IMPLICIT Identifier OPTIONAL
}

ReportPoolSemaphoreStatus-Response ::= SEQUENCE {
    listOfNamedTokens	 [0] IMPLICIT SEQUENCE OF CHOICE {
            freeNamedToken	 [0] IMPLICIT Identifier,
            ownedNamedToken	 [1] IMPLICIT Identifier,
            hungNamedToken	 [2] IMPLICIT Identifier
        },
    moreFollows	 [1] IMPLICIT BOOLEAN DEFAULT TRUE
}

ReportSemaphoreEntryStatus-Request ::= SEQUENCE {
    semaphoreName	 [0] ObjectName,
    state	 [1] IMPLICIT INTEGER {
        queued(0),
        owner(1),
        hung(2)
    } (0..2),
    entryIDToStartAfter	 [2] IMPLICIT OCTET STRING OPTIONAL
}

ReportSemaphoreEntryStatus-Response ::= SEQUENCE {
    listOfSemaphoreEntry	 [0] IMPLICIT SEQUENCE OF SemaphoreEntry,
    moreFollows	 [1] IMPLICIT BOOLEAN DEFAULT TRUE
}

SemaphoreEntry ::= SEQUENCE {
    entryID	 [0] IMPLICIT OCTET STRING,
    entryClass	 [1] IMPLICIT INTEGER {
        simple(0),
        modifier(1)
    } (0..1),
    applicationReference	 [2] ApplicationReference,
    namedToken	 [3] IMPLICIT Identifier OPTIONAL,
    priority	 [4] IMPLICIT Priority DEFAULT normalPriority,
    remainingTimeOut	 [5] IMPLICIT Unsigned32 OPTIONAL,
    abortOnTimeOut	 [6] IMPLICIT BOOLEAN OPTIONAL,
    relinquishIfConnectionLost	 [7] IMPLICIT BOOLEAN DEFAULT TRUE
}

AttachToSemaphore ::= SEQUENCE {
    semaphoreName	 [0] ObjectName,
    namedToken	 [1] IMPLICIT Identifier OPTIONAL,
    priority	 [2] IMPLICIT Priority DEFAULT normalPriority,
    acceptableDelay	 [3] IMPLICIT Unsigned32 OPTIONAL,
    controlTimeOut	 [4] IMPLICIT Unsigned32 OPTIONAL,
    abortOnTimeOut	 [5] IMPLICIT BOOLEAN OPTIONAL,
    relinquishIfConnectionLost	 [6] IMPLICIT BOOLEAN DEFAULT TRUE
}

Input-Request ::= SEQUENCE {
    operatorStationName	 [0] IMPLICIT Identifier,
    echo	 [1] IMPLICIT BOOLEAN DEFAULT TRUE,
    listOfPromptData	 [2] IMPLICIT SEQUENCE OF MMSString OPTIONAL,
    inputTimeOut	 [3] IMPLICIT Unsigned32 OPTIONAL
}

Input-Response ::= MMSString

Output-Request ::= SEQUENCE {
    operatorStationName	 [0] IMPLICIT Identifier,
    listOfOutputData	 [1] IMPLICIT SEQUENCE OF MMSString
}

Output-Response ::= NULL

TriggerEvent-Request ::= SEQUENCE {
    eventConditionName	 [0] ObjectName,
    priority	 [1] IMPLICIT Priority OPTIONAL
}

TriggerEvent-Response ::= NULL

EventNotification ::= SEQUENCE {
    eventEnrollmentName	 [0] ObjectName,
    eventConditionName	 [1] ObjectName,
    severity	 [2] IMPLICIT Severity,
    currentState	 [3] IMPLICIT EC-State OPTIONAL,
    transitionTime	 [4] EventTime,
    notificationLost	 [6] IMPLICIT BOOLEAN DEFAULT FALSE,
    alarmAcknowledgmentRule	 [7] IMPLICIT AlarmAckRule OPTIONAL,
    actionResult	 [8] IMPLICIT SEQUENCE {
        eventActionName	 ObjectName,
        successOrFailure	 CHOICE {
            success	 [0] IMPLICIT SEQUENCE {
                confirmedServiceResponse	 ConfirmedServiceResponse,
                cs-Response-Detail	 [79] Response-Detail OPTIONAL
            },
            failure	 [1] IMPLICIT SEQUENCE {
                modifierPosition	 [0] IMPLICIT Unsigned32 OPTIONAL,
                serviceError	 [1] IMPLICIT ServiceError
            }
        }
    } OPTIONAL
}

CS-EventNotification ::= [0] CHOICE {
    string	 [0] IMPLICIT VisibleString,
    index	 [1] IMPLICIT INTEGER,
    noEnhancement	 NULL
}

AcknowledgeEventNotification-Request ::= SEQUENCE {
    eventEnrollmentName	 [0] ObjectName,
    acknowledgedState	 [2] IMPLICIT EC-State,
    timeOfAcknowledgedTransition	 [3] EventTime
}

AcknowledgeEventNotification-Response ::= NULL

GetAlarmSummary-Request ::= SEQUENCE {
    enrollmentsOnly	 [0] IMPLICIT BOOLEAN DEFAULT TRUE,
    activeAlarmsOnly	 [1] IMPLICIT BOOLEAN DEFAULT TRUE,
    acknowledgementFilter	 [2] IMPLICIT INTEGER {
        not-acked(0),
        acked(1),
        all(2)
    } (0..2) DEFAULT not-acked,
    severityFilter	 [3] IMPLICIT SEQUENCE {
        mostSevere	 [0] IMPLICIT Unsigned8,
        leastSevere	 [1] IMPLICIT Unsigned8
    } DEFAULT { mostSevere 0, leastSevere 127 },
    continueAfter	 [5] ObjectName OPTIONAL
}

GetAlarmSummary-Response ::= SEQUENCE {
    listOfAlarmSummary	 [0] IMPLICIT SEQUENCE OF AlarmSummary,
    moreFollows	 [1] IMPLICIT BOOLEAN DEFAULT FALSE
}

AlarmSummary ::= SEQUENCE {
    eventConditionName	 [0] ObjectName,
    severity	 [1] IMPLICIT Unsigned8,
    currentState	 [2] IMPLICIT EC-State,
    unacknowledgedState	 [3] IMPLICIT INTEGER {
        none(0),
        active(1),
        idle(2),
        both(3)
    } (0..3),
    displayEnhancement	 [4] EN-Additional-Detail OPTIONAL,
    timeOfLastTransitionToActive	 [5] EventTime OPTIONAL,
    timeOfLastTransitionToIdle	 [6] EventTime OPTIONAL
}

EN-Additional-Detail ::= [0] CHOICE {
    string	 [0] IMPLICIT VisibleString,
    index	 [1] IMPLICIT INTEGER,
    noEnhancement	 NULL
}

GetAlarmEnrollmentSummary-Request ::= SEQUENCE {
    enrollmentsOnly	 [0] IMPLICIT BOOLEAN DEFAULT TRUE,
    activeAlarmsOnly	 [1] IMPLICIT BOOLEAN DEFAULT TRUE,
    acknowledgementFilter	 [2] IMPLICIT INTEGER {
        not-acked(0),
        acked(1),
        all(2)
    } (0..2) DEFAULT not-acked,
    severityFilter	 [3] IMPLICIT SEQUENCE {
        mostSevere	 [0] IMPLICIT Unsigned8,
        leastSevere	 [1] IMPLICIT Unsigned8
    } DEFAULT { mostSevere 0, leastSevere 127 },
    continueAfter	 [5] ObjectName OPTIONAL
}

GetAlarmEnrollmentSummary-Response ::= SEQUENCE {
    listOfAlarmEnrollmentSummary	 [0] IMPLICIT SEQUENCE OF AlarmEnrollmentSummary,
    moreFollows	 [1] IMPLICIT BOOLEAN DEFAULT FALSE
}

AlarmEnrollmentSummary ::= SEQUENCE {
    eventEnrollmentName	 [0] ObjectName,
    clientApplication	 [2] ApplicationReference OPTIONAL,
    severity	 [3] IMPLICIT Unsigned8,
    currentState	 [4] IMPLICIT EC-State,
    displayEnhancement	 [5] EN-Additional-Detail OPTIONAL,
    notificationLost	 [6] IMPLICIT BOOLEAN DEFAULT FALSE,
    alarmAcknowledgmentRule	 [7] IMPLICIT AlarmAckRule,
    enrollmentState	 [8] IMPLICIT EE-State OPTIONAL,
    timeOfLastTransitionToActive	 [9] EventTime OPTIONAL,
    timeActiveAcknowledged	 [10] EventTime OPTIONAL,
    timeOfLastTransitionToIdle	 [11] EventTime OPTIONAL,
    timeIdleAcknowledged	 [12] EventTime OPTIONAL
}

AttachToEventCondition ::= SEQUENCE {
    eventEnrollmentName	 [0] ObjectName,
    eventConditionName	 [1] ObjectName,
    causingTransitions	 [2] IMPLICIT Transitions,
    acceptableDelay	 [3] IMPLICIT Unsigned32 OPTIONAL
}

DefineEventCondition-Request ::= SEQUENCE {
    eventConditionName	 [0] ObjectName,
    class	 [1] IMPLICIT EC-Class,
    priority	 [2] IMPLICIT Priority DEFAULT normalPriority,
    severity	 [3] IMPLICIT Unsigned8 DEFAULT normalSeverity,
    alarmSummaryReports	 [4] IMPLICIT BOOLEAN OPTIONAL,
    monitoredVariable	 [6] VariableSpecification OPTIONAL,
    evaluationInterval	 [7] IMPLICIT Unsigned32 OPTIONAL
}

DefineEventCondition-Response ::= NULL

CS-DefineEventCondition-Request ::= [0] CHOICE {
    string	 [0] IMPLICIT VisibleString,
    index	 [1] IMPLICIT INTEGER,
    noEnhancement	 NULL
}

DeleteEventCondition-Request ::= CHOICE {
    specific	 [0] IMPLICIT SEQUENCE OF ObjectName,
    aa-specific	 [1] IMPLICIT NULL,
    domain	 [2] IMPLICIT Identifier,
    vmd	 [3] IMPLICIT NULL
}

DeleteEventCondition-Response ::= Unsigned32

GetEventConditionAttributes-Request ::= ObjectName

GetEventConditionAttributes-Response ::= SEQUENCE {
    mmsDeletable	 [0] IMPLICIT BOOLEAN DEFAULT FALSE,
    class	 [1] IMPLICIT EC-Class,
    priority	 [2] IMPLICIT Priority DEFAULT normalPriority,
    severity	 [3] IMPLICIT Unsigned8 DEFAULT normalSeverity,
    alarmSummaryReports	 [4] IMPLICIT BOOLEAN DEFAULT FALSE,
    monitoredVariable	 [6] CHOICE {
        variableReference	 [0] VariableSpecification,
        undefined	 [1] IMPLICIT NULL
    } OPTIONAL,
    evaluationInterval	 [7] IMPLICIT Unsigned32 OPTIONAL,
    accessControlList	 [8] IMPLICIT Identifier OPTIONAL
}

CS-GetEventConditionAttributes-Response ::= SEQUENCE {
    groupPriorityOverride	 [0] CHOICE {
        priority	 [0] IMPLICIT Priority,
        undefined	 [1] IMPLICIT NULL
    } OPTIONAL,
    listOfReferencingECL	 [1] IMPLICIT SEQUENCE OF ObjectName OPTIONAL,
    displayEnhancement	 [2] CHOICE {
        string	 [0] IMPLICIT VisibleString,
        index	 [1] IMPLICIT INTEGER,
        noEnhancement	 [2] IMPLICIT NULL
    }
}

ReportEventConditionStatus-Request ::= ObjectName

ReportEventConditionStatus-Response ::= SEQUENCE {
    currentState	 [0] IMPLICIT EC-State,
    numberOfEventEnrollments	 [1] IMPLICIT Unsigned32,
    enabled	 [2] IMPLICIT BOOLEAN OPTIONAL,
    timeOfLastTransitionToActive	 [3] EventTime OPTIONAL,
    timeOfLastTransitionToIdle	 [4] EventTime OPTIONAL
}

AlterEventConditionMonitoring-Request ::= SEQUENCE {
    eventConditionName	 [0] ObjectName,
    enabled	 [1] IMPLICIT BOOLEAN OPTIONAL,
    priority	 [2] IMPLICIT Priority OPTIONAL,
    alarmSummaryReports	 [3] IMPLICIT BOOLEAN OPTIONAL,
    evaluationInterval	 [4] IMPLICIT Unsigned32 OPTIONAL
}

AlterEventConditionMonitoring-Response ::= NULL

CS-AlterEventConditionMonitoring-Request ::= SEQUENCE {
    changeDisplay	 CHOICE {
        string	 [0] IMPLICIT VisibleString,
        index	 [1] IMPLICIT INTEGER,
        noEnhancement	 [2] NULL
    } OPTIONAL
}

DefineEventAction-Request ::= SEQUENCE {
    eventActionName	 [0] ObjectName,
    listOfModifier	 [1] IMPLICIT SEQUENCE OF Modifier OPTIONAL,
    confirmedServiceRequest	 [2] ConfirmedServiceRequest,
    cs-extension	 [79] Request-Detail OPTIONAL
}

DefineEventAction-Response ::= NULL

DeleteEventAction-Request ::= CHOICE {
    specific	 [0] IMPLICIT SEQUENCE OF ObjectName,
    aa-specific	 [1] IMPLICIT NULL,
    domain	 [3] IMPLICIT Identifier,
    vmd	 [4] IMPLICIT NULL
}

DeleteEventAction-Response ::= Unsigned32

GetEventActionAttributes-Request ::= ObjectName

GetEventActionAttributes-Response ::= SEQUENCE {
    mmsDeletable	 [0] IMPLICIT BOOLEAN DEFAULT FALSE,
    listOfModifier	 [1] IMPLICIT SEQUENCE OF Modifier,
    confirmedServiceRequest	 [2] ConfirmedServiceRequest,
    cs-extension	 [79] Request-Detail OPTIONAL,
    accessControlList	 [3] IMPLICIT Identifier OPTIONAL
}

ReportEventActionStatus-Request ::= ObjectName

ReportEventActionStatus-Response ::= Unsigned32

DefineEventEnrollment-Request ::= SEQUENCE {
    eventEnrollmentName	 [0] ObjectName,
    eventConditionName	 [1] ObjectName,
    eventConditionTransitions	 [2] IMPLICIT Transitions,
    alarmAcknowledgmentRule	 [3] IMPLICIT AlarmAckRule,
    eventActionName	 [4] ObjectName OPTIONAL,
    clientApplication	 [5] ApplicationReference OPTIONAL
}

DefineEventEnrollment-Response ::= NULL

DefineEventEnrollment-Error ::= ObjectName

CS-DefineEventEnrollment-Request ::= [0] CHOICE {
    string	 [0] IMPLICIT VisibleString,
    index	 [1] IMPLICIT INTEGER,
    noEnhancement	 NULL
}

DeleteEventEnrollment-Request ::= CHOICE {
    specific	 [0] IMPLICIT SEQUENCE OF ObjectName,
    ec	 [1] ObjectName,
    ea	 [2] ObjectName
}

DeleteEventEnrollment-Response ::= Unsigned32

GetEventEnrollmentAttributes-Request ::= SEQUENCE {
    scopeOfRequest	 [0] IMPLICIT INTEGER {
        specific(0),
        client(1),
        ec(2),
        ea(3)
    } (0..3) DEFAULT client,
    eventEnrollmentNames	 [1] IMPLICIT SEQUENCE OF ObjectName OPTIONAL,
    clientApplication	 [2] ApplicationReference OPTIONAL,
    eventConditionName	 [3] ObjectName OPTIONAL,
    eventActionName	 [4] ObjectName OPTIONAL,
    continueAfter	 [5] ObjectName OPTIONAL
}

GetEventEnrollmentAttributes-Response ::= SEQUENCE {
    listOfEEAttributes	 [0] IMPLICIT SEQUENCE OF EEAttributes,
    moreFollows	 [1] IMPLICIT BOOLEAN DEFAULT FALSE
}

EEAttributes ::= SEQUENCE {
    eventEnrollmentName	 [0] ObjectName,
    eventConditionName	 [1] CHOICE {
        eventCondition	 [0] ObjectName,
        undefined	 [1] IMPLICIT NULL
    },
    eventActionName	 [2] CHOICE {
        eventAction	 [0] ObjectName,
        undefined	 [1] IMPLICIT NULL
    } OPTIONAL,
    clientApplication	 [3] ApplicationReference OPTIONAL,
    mmsDeletable	 [4] IMPLICIT BOOLEAN DEFAULT FALSE,
    enrollmentClass	 [5] IMPLICIT EE-Class,
    duration	 [6] IMPLICIT EE-Duration DEFAULT current,
    invokeID	 [7] IMPLICIT Unsigned32 OPTIONAL,
    remainingAcceptableDelay	 [8] IMPLICIT Unsigned32 OPTIONAL,
    displayEnhancement	 [9] CHOICE {
        string	 [0] IMPLICIT VisibleString,
        index	 [1] IMPLICIT INTEGER,
        noEnhancement	 NULL
    },
    accessControlList	 [11] IMPLICIT Identifier OPTIONAL
}

ReportEventEnrollmentStatus-Request ::= ObjectName

ReportEventEnrollmentStatus-Response ::= SEQUENCE {
    eventConditionTransitions	 [0] IMPLICIT Transitions,
    notificationLost	 [1] IMPLICIT BOOLEAN DEFAULT FALSE,
    duration	 [2] IMPLICIT EE-Duration,
    alarmAcknowledgmentRule	 [3] IMPLICIT AlarmAckRule OPTIONAL,
    currentState	 [4] IMPLICIT EE-State
}

AlterEventEnrollment-Request ::= SEQUENCE {
    eventEnrollmentName	 [0] ObjectName,
    eventConditionTransitions	 [1] IMPLICIT Transitions OPTIONAL,
    alarmAcknowledgmentRule	 [2] IMPLICIT AlarmAckRule OPTIONAL
}

AlterEventEnrollment-Response ::= SEQUENCE {
    currentState	 [0] CHOICE {
        state	 [0] IMPLICIT EE-State,
        undefined	 [1] IMPLICIT NULL
    },
    transitionTime	 [1] EventTime
}

CS-AlterEventEnrollment-Request ::= SEQUENCE {
    changeDisplay	 CHOICE {
        string	 [0] IMPLICIT VisibleString,
        index	 [1] IMPLICIT INTEGER,
        noEnhancement	 [2] NULL
    } OPTIONAL
}

EE-State ::= INTEGER {
    disabled(0),
    idle(1),
    active(2),
    activeNoAckA(3),
    idleNoAckI(4),
    idleNoAckA(5),
    idleAcked(6),
    activeAcked(7),
    undefined(8)
}

DefineEventConditionList-Request ::= SEQUENCE {
    eventConditionListName	 [0] ObjectName,
    listOfEventConditionName	 [1] IMPLICIT SEQUENCE OF ObjectName,
    listOfEventConditionListName	 [2] IMPLICIT SEQUENCE OF ObjectName OPTIONAL
}

DefineEventConditionList-Response ::= NULL

DefineEventConditionList-Error ::= ObjectName

DeleteEventConditionList-Request ::= ObjectName

DeleteEventConditionList-Response ::= NULL

AddEventConditionListReference-Request ::= SEQUENCE {
    eventConditionListName	 [0] ObjectName,
    listOfEventConditionName	 [1] IMPLICIT SEQUENCE OF ObjectName,
    listOfEventConditionListName	 [2] IMPLICIT SEQUENCE OF ObjectName OPTIONAL
}

AddEventConditionListReference-Response ::= NULL

AddEventConditionListReference-Error ::= ObjectName

RemoveEventConditionListReference-Request ::= SEQUENCE {
    eventConditionListName	 [0] ObjectName,
    listOfEventConditionName	 [1] IMPLICIT SEQUENCE OF ObjectName,
    listOfEventConditionListName	 [2] IMPLICIT SEQUENCE OF ObjectName
}

RemoveEventConditionListReference-Response ::= NULL

RemoveEventConditionListReference-Error ::= CHOICE {
    eventCondition	 [0] ObjectName,
    eventConditionList	 [1] ObjectName
}

GetEventConditionListAttributes-Request ::= ObjectName

GetEventConditionListAttributes-Response ::= SEQUENCE {
    listOfEventConditionName	 [1] IMPLICIT SEQUENCE OF ObjectName,
    listOfEventConditionListName	 [2] IMPLICIT SEQUENCE OF ObjectName OPTIONAL
}

ReportEventConditionListStatus-Request ::= SEQUENCE {
    eventConditionListName	 [0] ObjectName,
    continueAfter	 [1] IMPLICIT Identifier OPTIONAL
}

ReportEventConditionListStatus-Response ::= SEQUENCE {
    listOfEventConditionStatus	 [1] IMPLICIT SEQUENCE OF EventConditionStatus,
    moreFollows	 [2] IMPLICIT BOOLEAN DEFAULT TRUE
}

EventConditionStatus ::= SEQUENCE {
    eventConditionName	 [0] ObjectName,
    currentState	 [1] IMPLICIT EC-State,
    numberOfEventEnrollments	 [2] IMPLICIT Unsigned32,
    enabled	 [3] IMPLICIT BOOLEAN OPTIONAL,
    timeOfLastTransitionToActive	 [4] EventTime OPTIONAL,
    timeOfLastTransitionToIdle	 [5] EventTime OPTIONAL
}

AlterEventConditionListMonitoring-Request ::= SEQUENCE {
    eventConditionListName	 [0] ObjectName,
    enabled	 [1] IMPLICIT BOOLEAN,
    priorityChange	 [2] CHOICE {
        priorityValue	 [0] IMPLICIT INTEGER,
        priorityReset	 [1] IMPLICIT NULL
    } OPTIONAL
}

AlterEventConditionListMonitoring-Response ::= NULL

ReadJournal-Request ::= SEQUENCE {
    journalName	 [0] ObjectName,
    rangeStartSpecification	 [1] CHOICE {
        startingTime	 [0] IMPLICIT TimeOfDay,
        startingEntry	 [1] IMPLICIT OCTET STRING
    } OPTIONAL,
    rangeStopSpecification	 [2] CHOICE {
        endingTime	 [0] IMPLICIT TimeOfDay,
        numberOfEntries	 [1] IMPLICIT Integer32
    } OPTIONAL,
    listOfVariables	 [4] IMPLICIT SEQUENCE OF VisibleString OPTIONAL,
    entryToStartAfter	 [5] IMPLICIT SEQUENCE {
        timeSpecification	 [0] IMPLICIT TimeOfDay,
        entrySpecification	 [1] IMPLICIT OCTET STRING
    } OPTIONAL
}

ReadJournal-Response ::= SEQUENCE {
    listOfJournalEntry	 [0] IMPLICIT SEQUENCE OF JournalEntry,
    moreFollows	 [1] IMPLICIT BOOLEAN DEFAULT FALSE
}

JournalEntry ::= SEQUENCE {
    entryIdentifier	 [0] IMPLICIT OCTET STRING,
    originatingApplication	 [1] ApplicationReference,
    entryContent	 [2] IMPLICIT EntryContent
}

WriteJournal-Request ::= SEQUENCE {
    journalName	 [0] ObjectName,
    listOfJournalEntry	 [1] IMPLICIT SEQUENCE OF EntryContent
}

WriteJournal-Response ::= NULL

InitializeJournal-Request ::= SEQUENCE {
    journalName	 [0] ObjectName,
    limitSpecification	 [1] IMPLICIT SEQUENCE {
        limitingTime	 [0] IMPLICIT TimeOfDay,
        limitingEntry	 [1] IMPLICIT OCTET STRING OPTIONAL
    } OPTIONAL
}

InitializeJournal-Response ::= Unsigned32

ReportJournalStatus-Request ::= ObjectName

ReportJournalStatus-Response ::= SEQUENCE {
    currentEntries	 [0] IMPLICIT Unsigned32,
    mmsDeletable	 [1] IMPLICIT BOOLEAN,
    accessControlList	 [2] IMPLICIT Identifier OPTIONAL
}

CreateJournal-Request ::= SEQUENCE {
    journalName	 [0] ObjectName
}

CreateJournal-Response ::= NULL

DeleteJournal-Request ::= SEQUENCE {
    journalName	 [0] ObjectName
}

DeleteJournal-Response ::= NULL

EntryContent ::= SEQUENCE {
    occurrenceTime	 [0] IMPLICIT TimeOfDay,
    entryForm	 CHOICE {
        data	 [2] IMPLICIT SEQUENCE {
            event	 [0] IMPLICIT SEQUENCE {
                eventConditionName	 [0] ObjectName,
                currentState	 [1] IMPLICIT EC-State
            } OPTIONAL,
            listOfVariables	 [1] IMPLICIT SEQUENCE OF Journal-Variable OPTIONAL
        },
        annotation	 [3] MMSString
    }
}

-- MMS-Environment-1 { iso standard 9506 part(2) mms-environment-version1(4)}
-- DEFINITIONS ::= BEGIN
-- EXPORTS
-- ApplicationReference,
-- Authentication-value;

ApplicationReference ::= SEQUENCE {
    ap-title	 [0] ACSE-1.AP-title OPTIONAL,
    ap-invocation-id	 [1] ACSE-1.AP-invocation-identifier OPTIONAL,
    ae-qualifier	 [2] ACSE-1.AE-qualifier OPTIONAL,
    ae-invocation-id	 [3] ACSE-1.AE-invocation-identifier OPTIONAL
}

-- END (MMS-Environment-1)

ObtainFile-Request ::= SEQUENCE {
    sourceFileServer	 [0] IMPLICIT ApplicationReference OPTIONAL,
    sourceFile	 [1] IMPLICIT FileName,
    destinationFile	 [2] IMPLICIT FileName
}

ObtainFile-Response ::= NULL

ObtainFile-Error ::= INTEGER {
    source-file(0),
    destination-file(1)
} (0..1)

FileOpen-Request ::= SEQUENCE {
    fileName	 [0] IMPLICIT FileName,
    initialPosition	 [1] IMPLICIT Unsigned32
}

FileOpen-Response ::= SEQUENCE {
    frsmID	 [0] IMPLICIT Integer32,
    fileAttributes	 [1] IMPLICIT FileAttributes
}

FileRead-Request ::= Integer32

FileRead-Response ::= SEQUENCE {
    fileData	 [0] IMPLICIT OCTET STRING,
    moreFollows	 [1] IMPLICIT BOOLEAN DEFAULT TRUE
}

FileRename-Request ::= SEQUENCE {
    currentFileName	 [0] IMPLICIT FileName,
    newFileName	 [1] IMPLICIT FileName
}

FileRename-Response ::= NULL

FileRename-Error ::= INTEGER {
    source-file(0),
    destination-file(1)
} (0..1)

FileDelete-Request ::= FileName

FileDelete-Response ::= NULL

FileClose-Request ::= Integer32

FileClose-Response ::= NULL

FileDirectory-Request ::= SEQUENCE {
    fileSpecification	 [0] IMPLICIT FileName OPTIONAL,
    continueAfter	 [1] IMPLICIT FileName OPTIONAL
}

FileDirectory-Response ::= SEQUENCE {
    listOfDirectoryEntry	 [0] SEQUENCE OF DirectoryEntry,
    moreFollows	 [1] IMPLICIT BOOLEAN DEFAULT FALSE
}

DirectoryEntry ::= SEQUENCE {
    fileName	 [0] IMPLICIT FileName,
    fileAttributes	 [1] IMPLICIT FileAttributes
}

FileAttributes ::= SEQUENCE {
    sizeOfFile	 [0] IMPLICIT Unsigned32,
    lastModified	 [1] IMPLICIT GeneralizedTime OPTIONAL
}

ScatteredAccessDescription ::= SEQUENCE OF SEQUENCE {
        componentName	 [0] IMPLICIT Identifier OPTIONAL,
        variableSpecification	 [1] VariableSpecification,
        alternateAccess	 [2] IMPLICIT AlternateAccess OPTIONAL
    }

DefineScatteredAccess-Request ::= SEQUENCE {
    scatteredAccessName	 [0] ObjectName,
    scatteredAccessDescription	 [1] IMPLICIT ScatteredAccessDescription
}

DefineScatteredAccess-Response ::= NULL

GetScatteredAccessAttributes-Request ::= ObjectName

GetScatteredAccessAttributes-Response ::= SEQUENCE {
    mmsDeletable	 [0] IMPLICIT BOOLEAN,
    scatteredAccessDescription	 [1] IMPLICIT ScatteredAccessDescription,
    accessControlList	 [2] IMPLICIT Identifier OPTIONAL
}

-- END

-- MMS-Object-Module-1 { iso standard 9506 part(1) mms-object-model-version1(2) }
-- DEFINITIONS ::= BEGIN
--  This ASN.1 specification has been checked for conformance with the
-- ASN.1 standard by the OSS ASN.1 Tools.
--

-- EXPORTS AccessCondition,
-- AdditionalCBBOptions,
-- AdditionalSupportOptions,
-- Address,
-- AlarmAckRule,
-- Control-State,
-- DomainState,
-- EC-State,
-- EC-Class,
-- EE-Duration,
-- EE-Class,
-- EventTime,
-- Journal-Variable,
-- LogicalStatus,
-- Modifier,
-- normalPriority,
-- normalSeverity,
-- ParameterSupportOptions,
-- PhysicalStatus,
-- Priority,
-- ProgramInvocationState,
-- Running-Mode,
-- ServiceSupportOptions,
-- Severity,
-- Transitions,
-- TypeDescription,
-- ULState,
-- VMDState;

-- IMPORTS ApplicationReference,
-- Authentication-value FROM
-- MMS-Environment-1 { iso standard 9506 part(2) mms-environment-version1(4) }
-- AlternateAccess,
-- ConfirmedServiceRequest,
-- AttachToSemaphore,
-- AttachToEventCondition,
-- Data,
-- EE-State,
-- Identifier,
-- Integer8,
-- Integer32,
-- MMSString,
-- MMS255String,
-- ObjectName,
-- TimeOfDay,
-- TypeSpecification,
-- Unsigned32,
-- Unsigned8 FROM
-- ISO-9506-MMS-1 { iso standard 9506 part(2) mms-abstract-syntax-version1(1) };

Modifier ::= CHOICE {
    eventModifier	 [0] IMPLICIT AttachToEventCondition,
    semaphoreModifier	 [1] IMPLICIT AttachToSemaphore
}

ModifierStep ::= SEQUENCE {
    modifierID	 INTEGER,
    modifier	 Modifier
}

ServiceSupportOptions ::= BIT STRING {
    status(0),
    getNameList(1),
    identify(2),
    rename(3),
    read(4),
    write(5),
    getVariableAccessAttributes(6),
    defineNamedVariable(7),
    defineScatteredAccess(8),
    getScatteredAccessAttributes(9),
    deleteVariableAccess(10),
    defineNamedVariableList(11),
    getNamedVariableListAttributes(12),
    deleteNamedVariableList(13),
    defineNamedType(14),
    getNamedTypeAttributes(15),
    deleteNamedType(16),
    input(17),
    output(18),
    takeControl(19),
    relinquishControl(20),
    defineSemaphore(21),
    deleteSemaphore(22),
    reportSemaphoreStatus(23),
    reportPoolSemaphoreStatus(24),
    reportSemaphoreEntryStatus(25),
    initiateDownloadSequence(26),
    downloadSegment(27),
    terminateDownloadSequence(28),
    initiateUploadSequence(29),
    uploadSegment(30),
    terminateUploadSequence(31),
    requestDomainDownload(32),
    requestDomainUpload(33),
    loadDomainContent(34),
    storeDomainContent(35),
    deleteDomain(36),
    getDomainAttributes(37),
    createProgramInvocation(38),
    deleteProgramInvocation(39),
    start(40),
    stop(41),
    resume(42),
    reset(43),
    kill(44),
    getProgramInvocationAttributes(45),
    obtainFile(46),
    defineEventCondition(47),
    deleteEventCondition(48),
    getEventConditionAttributes(49),
    reportEventConditionStatus(50),
    alterEventConditionMonitoring(51),
    triggerEvent(52),
    defineEventAction(53),
    deleteEventAction(54),
    getEventActionAttributes(55),
    reportEventActionStatus(56),
    defineEventEnrollment(57),
    deleteEventEnrollment(58),
    alterEventEnrollment(59),
    reportEventEnrollmentStatus(60),
    getEventEnrollmentAttributes(61),
    acknowledgeEventNotification(62),
    getAlarmSummary(63),
    getAlarmEnrollmentSummary(64),
    readJournal(65),
    writeJournal(66),
    initializeJournal(67),
    reportJournalStatus(68),
    createJournal(69),
    deleteJournal(70),
    getCapabilityList(71),
    fileOpen(72),
    fileRead(73),
    fileClose(74),
    fileRename(75),
    fileDelete(76),
    fileDirectory(77),
    unsolicitedStatus(78),
    informationReport(79),
    eventNotification(80),
    attachToEventCondition(81),
    attachToSemaphore(82),
    conclude(83),
    cancel(84),
    getDataExchangeAttributes(85),
    exchangeData(86),
    defineAccessControlList(87),
    getAccessControlListAttributes(88),
    reportAccessControlledObjects(89),
    deleteAccessControlList(90),
    alterAccessControl(91),
    reconfigureProgramInvocation(92)
} -- (SIZE(93))

ParameterSupportOptions ::= BIT STRING {
    str1(0),
    str2(1),
    vnam(2),
    valt(3),
    vadr(4),
    vsca(5),
    tpy(6),
    vlis(7),
    cei(10),
    aco(11),
    sem(12),
    csr(13),
    csnc(14),
    csplc(15),
    cspi(16),
    char(17)
} -- (SIZE(18))

AdditionalSupportOptions ::= BIT STRING {
    vMDStop(0),
    vMDReset(1),
    select(2),
    alterProgramInvocationAttributes(3),
    initiateUnitControlLoad(4),
    unitControlLoadSegment(5),
    unitControlUpload(6),
    startUnitControl(7),
    stopUnitControl(8),
    createUnitControl(9),
    addToUnitControl(10),
    removeFromUnitControl(11),
    getUnitControlAttributes(12),
    loadUnitControlFromFile(13),
    storeUnitControlToFile(14),
    deleteUnitControl(15),
    defineEventConditionList(16),
    deleteEventConditionList(17),
    addEventConditionListReference(18),
    removeEventConditionListReference(19),
    getEventConditionListAttributes(20),
    reportEventConditionListStatus(21),
    alterEventConditionListMonitoring(22)
} -- (SIZE(23))

AdditionalCBBOptions ::= BIT STRING {
    des(0),
    dei(1),
    recl(2)
} -- (SIZE(3))

AccessCondition ::= CHOICE {
    never	 [0] IMPLICIT NULL,
    semaphore	 [1] Identifier,
    user	 [2] CHOICE {
        association	 ApplicationReference,
        none	 NULL
    },
    password	 [3] Authentication-value,
    joint	 [4] IMPLICIT SEQUENCE OF AccessCondition,
    alternate	 [5] IMPLICIT SEQUENCE OF AccessCondition
}

DomainState ::= INTEGER {
    non-existent(0),
    loading(1),
    ready(2),
    in-use(3),
    complete(4),
    incomplete(5),
    d1(7),
    d2(8),
    d3(9),
    d4(10),
    d5(11),
    d6(12),
    d7(13),
    d8(14),
    d9(15)
} (0..15)

ProgramInvocationState ::= INTEGER {
    non-existent(0),
    unrunnable(1),
    idle(2),
    running(3),
    stopped(4),
    starting(5),
    stopping(6),
    resuming(7),
    resetting(8)
} (0..8)

TypeDescription ::= CHOICE {
    array	 [1] IMPLICIT SEQUENCE {
        packed	 [0] IMPLICIT BOOLEAN DEFAULT FALSE,
        numberOfElements	 [1] IMPLICIT Unsigned32,
        elementType	 [2] TypeSpecification
    },
    structure	 [2] IMPLICIT SEQUENCE {
        packed	 [0] IMPLICIT BOOLEAN DEFAULT FALSE,
        components	 [1] IMPLICIT SEQUENCE OF SEQUENCE {
                componentName	 [0] IMPLICIT Identifier OPTIONAL,
                componentType	 [1] TypeSpecification
            }
    },
    boolean	 [3] IMPLICIT NULL,
    bit-string	 [4] IMPLICIT Integer32,
    integer	 [5] IMPLICIT Unsigned8,
    unsigned	 [6] IMPLICIT Unsigned8,
    floating-point	 [7] IMPLICIT SEQUENCE {
        format-width	 Unsigned8,
        exponent-width	 Unsigned8
    },
    octet-string	 [9] IMPLICIT Integer32,
    visible-string	 [10] IMPLICIT Integer32,
    generalized-time	 [11] IMPLICIT NULL,
    binary-time	 [12] IMPLICIT BOOLEAN,
    bcd	 [13] IMPLICIT Unsigned8,
    objId	 [15] IMPLICIT NULL,
    mMSString	 [16] IMPLICIT Integer32,
    utc-time    [17] IMPLICIT UtcTime
}

Address ::= CHOICE {
    numericAddress	 [0] IMPLICIT Unsigned32,
    symbolicAddress	 [1] MMSString,
    unconstrainedAddress	 [2] IMPLICIT OCTET STRING
}

Priority ::= INTEGER (0..127)

normalPriority Priority ::= 64

Severity ::= INTEGER (0..127)

normalSeverity Severity ::= 64

EventTime ::= CHOICE {
    timeOfDay	 [0] IMPLICIT TimeOfDay,
    timeSequenceIdentifier	 [1] IMPLICIT Unsigned32,
    undefined	 [2] IMPLICIT NULL
}

EC-State ::= INTEGER {
    disabled(0),
    idle(1),
    active(2)
} (0..2)

AlarmAckRule ::= INTEGER {
    none(0),
    simple(1),
    ack-active(2),
    ack-all(3)
} (0..3)

Transitions ::= BIT STRING {
    idle-to-disabled(0),
    active-to-disabled(1),
    disabled-to-idle(2),
    active-to-idle(3),
    disabled-to-active(4),
    idle-to-active(5),
    any-to-deleted(6)
} -- (SIZE(7))

EC-Class ::= INTEGER {
    network-triggered(0),
    monitored(1)
} (0..1)

EE-Class ::= INTEGER {
    modifier(0),
    notification(1)
} (0..1)

EE-Duration ::= INTEGER {
    current(0),
    permanent(1)
} (0..1)

Journal-Variable ::= SEQUENCE {
    variableTag	 MMS255String,
    valueSpecification	 Data
}

-- END (MMS-Object-Module-1)

END -- ISO-9506-MMS-1
